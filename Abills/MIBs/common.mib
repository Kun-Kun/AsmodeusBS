--***************************************************************************
--***************************************************************************

  COMMON-MIB DEFINITIONS ::= BEGIN


  IMPORTS
    IpAddress            FROM RFC1155-SMI
    Counter              FROM RFC1155-SMI
    TimeTicks            FROM RFC1155-SMI
    DisplayString        FROM RFC1213-MIB
    OBJECT-TYPE          FROM RFC-1212
    TRAP-TYPE            FROM RFC-1215


    mfr2                 FROM CORPORAT-MIB
    authenticate         FROM CORPORAT-MIB
    listener             FROM CORPORAT-MIB
    calldialin           FROM CORPORAT-MIB
    testmanager          FROM CORPORAT-MIB
    installation         FROM CORPORAT-MIB
    dropinsert           FROM CORPORAT-MIB
    calldialout          FROM CORPORAT-MIB
    framerelay           FROM CORPORAT-MIB
    filterip             FROM CORPORAT-MIB
    genroute             FROM CORPORAT-MIB
    dax                  FROM CORPORAT-MIB
    dsp                  FROM CORPORAT-MIB
    alarm                FROM CORPORAT-MIB
    dnis                 FROM CORPORAT-MIB
    ppp                  FROM CORPORAT-MIB
    location             FROM CORPORAT-MIB
    modem                FROM CORPORAT-MIB
    sysMgmt              FROM CORPORAT-MIB ;

    lineSig      OBJECT IDENTIFIER ::= { mfr2 1 }
    interRegSig  OBJECT IDENTIFIER ::= { mfr2 2 }

                  
  --*************************************************************************
  --*************************************************************************
  --                         New SYNTAX Types
  --*************************************************************************
  --*************************************************************************

  -- The system requires that these be defined as the decimal
  -- equavalant of the binary.

  LineCode ::= INTEGER {
                 abcd-0000(0),
                 abcd-0001(1),
                 abcd-0010(2),
                 abcd-0011(3),
                 abcd-0100(4),
                 abcd-0101(5),
                 abcd-0110(6),
                 abcd-0111(7),
                 abcd-1000(8),
                 abcd-1001(9),
                 abcd-1010(10),
                 abcd-1011(11),
                 abcd-1100(12),
                 abcd-1101(13),
                 abcd-1110(14),
                 abcd-1111(15)
                 }

  RespCode ::= INTEGER {
                 a1(1),
                 a2(2),
                 a3(3),
                 a4(4),
                 a5(5),
                 a6(6),
                 a7(7),
                 a8(8),
                 a9(9),
                 a10(10),
                 a11(11),
                 a12(12),
                 a13(13),
                 a14(14),
                 a15(15)
                 }

  DialinState ::= INTEGER {
                  ringing(1),
                  connecting(2),
                  lcpNegotiate(3),
                  authenticating(4),
                  tcpEstablish(5),
                  online(6),
                  disconnecting(7),
                  cleaningup(8),
                  dead(9),
                  kill(10),
                  bury(11),
                  l2tpTunneled(12),
                  waitCallback(13)
                  }

  TerminateReason ::= INTEGER {
                 stillActive(0),
                 notKnown(1),
                 idleTimeout(2),
                 killed(3),
                 takeLinkDown(4),
                 userHangup(5),
                 modemCanNotConnect(6),
                 modemError(7),
                 pppClose(8),
                 lcpClose(9),
                 loginTimeOut(10),
                 userTerminated(11),
                 noPoll(12),
                 ipcPutMsgErr(13),
                 invalidAuthMsg(14),
                 pollErr(15),
                 ioctlErr(16),
                 pppPutMsgErr(17),
                 dspIoctlErr(18),
                 timerErr(19),
                 authClean(20),
                 maxNumCalls(21),
                 pppOpenErr(22),
                 ipLinkErr(23),
                 notPapReq(24),
                 pppLinkErr(25),
                 tcpOpenErr(26),
                 tcpPushErr(27),
                 tcpPutMsgErr(28),
                 invalidPrim(29),
                 noIpPoolAddr(30),
                 noIpAddr(31),
                 maxLoginAttempts(32),
                 noTimers(33),
                 tcpLinkErr(34),
                 dspLinkErr(35),
                 dspPutMsgErr(36),
                 noDsp(37),
                 lisIpcErr(38),
                 dspOpenErr(39),
                 invalidCode(40),
                 callContention(41),
                 dspCommErr(42),
                 unknownBearerContent(43),
                 invalidDefaults(44),
                 noDspAvailable(45),
                 dspOutOfState(46),
                 dspRequestUnsupported(47),
                 dspBadPrimitive(48),
                 papAuthenticationFailure(49),
                 papInvalidPacket(50),
                 authenServerTimeout(51),
                 authenAccountingTimeout(52),
                 unknownProtocol(53),
                 mfr2DisWaitCalled(54),
                 mfr2DisAckCalled(55),
                 mfr2DisAckLastCalled(56),
                 mfr2DisWaitCalling(57),
                 mfr2DisAckCalling(58),
                 mfr2DisAckLastCalling(59),
                 mfr2DisWhileComplete(60),
                 tcpSideClosure(61),
                 telnetError(62),
                 rloginError(63),
                 exceedsMultiLinkLimit(64),
                 lcpNegotiationFailure(65),
                 sessionTimeout(66),
                 tcpConnAborted(67),
                 tcpNoBuffers(68),
                 tcpConnRefused(69),
                 tcpConnReset(70),
                 tcpTimedOut(71),
                 noLnsIpAddr(72),
                 noDefaultLns(73),
                 vpnPeerRejected(74),
                 udpOpenErr(75),
                 udpBindErr(76),
                 l2tpOpenErr(77),
                 l2tpLinkErr(78),
                 reLinkErr(79),
                 l2tpCallDisconnected(80),
                 l2tpLNSConnectTimeout(81),
                 l2tpLACConnectTimeout(82),
                 v110disabled(83),
                 restarted(84),
                 noAnswer(85),
                 userBusy(86),
                 noChannelAvail(87),
                 callingback(88),
                 callComplete(89)
                 }

  Mfr2GroupBCode ::= INTEGER {
                 b1(1),
                 b5(5),
                 b6(6),
                 b7(7)
                 }
 
  LoginTechnique ::= INTEGER {
                 none(0),
                 textORpap(1),
                 text(2),
                 pap(3),
                 chap(4),
                 chapORpap(5),
                 textORchapORpap(6)
                 }

  IpPool     ::= DisplayString (SIZE (0..39))

  LineIndex  ::= INTEGER (1..'7fffffff'h)

  DnisStatus ::= INTEGER {
                 active(1),
                 notUsed(2),
                 destroy(3)
                 }

  DovbsConfig ::= INTEGER {
                  disable(0),
                  dovbs56k(1),
                  dovbs64k(2)
                  }

  DialedNumber         ::= DisplayString  (SIZE (0..80))

  AuthenticationString ::= DisplayString (SIZE (0..39))

  IpConfigCompression  ::= INTEGER {
                           none(1),
                           vj-tcp(2)
                           }

  EnabledDisabled      ::= INTEGER {
                           enabled(1),
                           disabled(2)
                           }

  Index                ::= INTEGER(1..2147483647)

  AccessLevel          ::= INTEGER {
                           passthru(1),
                           monitor(2),
                           change(3)
                           }

  LcpAuth              ::= INTEGER {
                          none(1),
                          pap(2),
                          chap(3),
                          msChap(4),
                          tacacs(5),
                          epd(6),
                          shivaPap(7)
                          }

  FcsSize              ::= INTEGER (0..128)


  MaxSlotId            ::= INTEGER (0..255)

  PppStates            ::= INTEGER {
                       restarting(1),
                       connecting(2),
                       lcpNegotiate(3),
                       authenticating(4),
                       pppUp(5),
                       disconnecting(6),
                       dead(7),
                       onlineBcp(8),
                       onlineIpcp(9),
                       restart(10),
                       kill(11),
                       bury(12)
                       }

  FilterIpPortCmp      ::= INTEGER {
                       noCompare(0),
                       equal(1),
                       lessThan(2),
                       greaterThan(3)
                       }

  FilterIpAddressCmp   ::= INTEGER {
                       equal(0),
                       notEqual(1)
                       }


  ModemModulation      ::= INTEGER {
                       unknown(0),
                       v21(1),
                       v22(2),
                       v32(3),
                       v34(4),
                       k56(5),
                       x2(6),
                       v90(7),
                       v110(8),
                       isdn64(9),
                       isdn56(10),
                       l2tp(11),
                       phase2(20),
                       answerAck(21),
                       v92(22),
                       moh(23),
                       v23(24)
                       }


  --*************************************************************************
  --*************************************************************************
  --                         Line Signalling for MFR2
  --*************************************************************************
  --*************************************************************************

  lineSigCountry OBJECT-TYPE
    SYNTAX      INTEGER {
                  ituStandard(1),
                  custom(2),
                  mexicoModified(3),
                  czechRepublic(4),
                  pbxDropOut(5),
                  brazil(6),
                  chinaR1(7),
                  southAfrica(8),
                  india(9)
                }
    ACCESS      read-write
    STATUS      mandatory
    DESCRIPTION "Specifying a particular country or ituStandard
                 defines the values of the remaining fields based
                 on the specs.  custom allows for any values in
                 the following fields."
    ::= { lineSig 1 }

  lineSigIdleCode OBJECT-TYPE
    SYNTAX      LineCode
    ACCESS      read-write
    STATUS      mandatory
    DESCRIPTION "Code to indicate that a line is not used."
    ::= { lineSig 2 }

  lineSigForwardSeize OBJECT-TYPE
    SYNTAX      LineCode
    ACCESS      read-write
    STATUS      mandatory
    DESCRIPTION "Code to indicate there is a desire to use a
                 line. "
    ::= { lineSig 3 }

  lineSigBackAck OBJECT-TYPE
    SYNTAX      LineCode
    ACCESS      read-write
    STATUS      mandatory
    DESCRIPTION "Code to indicate there is an agreement to use
                 a line."
    ::= { lineSig 4 }

  lineSigBackAnswer OBJECT-TYPE
    SYNTAX      LineCode
    ACCESS      read-write
    STATUS      mandatory
    DESCRIPTION "Code to indicate a call has been completed."
    ::= { lineSig 5 }

  lineSigMinTransTime OBJECT-TYPE
    SYNTAX      INTEGER
    ACCESS      read-write
    STATUS      mandatory
    DESCRIPTION "The minimum transition time in milliseconds."
    ::= { lineSig 6 }

  lineSigMinDetectTime OBJECT-TYPE
    SYNTAX      INTEGER
    ACCESS      read-write
    STATUS      mandatory
    DESCRIPTION "The minmum detect time in milliseconds."
    ::= { lineSig 7 }

  lineSigProtoTimeout OBJECT-TYPE
    SYNTAX      INTEGER
    ACCESS      read-write
    STATUS      mandatory
    DESCRIPTION "The time for a protocol timeout in milliseconds."
    ::= { lineSig 8 }


  --*************************************************************************
  --*************************************************************************
  --                    Interregister Signalling for MFR2
  --*************************************************************************
  --*************************************************************************

  interRegCalledNumDig OBJECT-TYPE
    SYNTAX      INTEGER
    ACCESS      read-write
    STATUS      mandatory
    DESCRIPTION "The number of digits expected for the
                 called number."
    ::= { interRegSig 1 }

  interRegCalledNumFirst OBJECT-TYPE
    SYNTAX      RespCode
    ACCESS      read-write
    STATUS      mandatory
    DESCRIPTION "The code specifying what is done after
                 every digit is sent except the last for
                 the called number."
    ::= { interRegSig 2 }

  interRegCalledNumLast OBJECT-TYPE
    SYNTAX      RespCode
    ACCESS      read-write
    STATUS      mandatory
    DESCRIPTION "The code specifying what is done after
                 the last digit is sent for the called
                 number."
    ::= { interRegSig 3 }

  interRegCallingNumDig OBJECT-TYPE
    SYNTAX      INTEGER
    ACCESS      read-write
    STATUS      mandatory
    DESCRIPTION "The number of digits expected for the
                 calling number."
    ::= { interRegSig 4 }

  interRegCallingNumFirst OBJECT-TYPE
    SYNTAX      RespCode
    ACCESS      read-write
    STATUS      mandatory
    DESCRIPTION "The code specifying what is done after
                 every digit is sent except the last
                 for the calling number."
    ::= { interRegSig 5 }

  interRegCallingNumLast OBJECT-TYPE
    SYNTAX      RespCode
    ACCESS      read-write
    STATUS      mandatory
    DESCRIPTION "The code specifying what is done after
                 the last digit is sent for the calling
                 number."
    ::= { interRegSig 6 }

  interRegGroupBAck OBJECT-TYPE
	  SYNTAX	    Mfr2GroupBCode
	  ACCESS	    read-write
	  STATUS	    mandatory
	  DESCRIPTION "The code sent when acking Group B digit to set-up
			  speech conditions"
	  ::= { interRegSig 7 }

  --*************************************************************************
  --*************************************************************************
  --                         LISTENER
  --*************************************************************************
  --*************************************************************************

  -- Define a table with entries for both of the links.  The indexing of this table
  -- will parallel the indexing of the DS1 MIB.
  linkTable OBJECT-TYPE
    SYNTAX      SEQUENCE OF LinkEntry
    ACCESS      not-accessible
    STATUS      mandatory
    DESCRIPTION "The Enterprise DS1 Configuration table."
    ::= { listener 1 }

  linkEntry OBJECT-TYPE
    SYNTAX       LinkEntry
    ACCESS       not-accessible
    STATUS       mandatory
    DESCRIPTION  "An entry in the Enterprise DS1 Configuration table."
    INDEX   { linkLineIndex }
    ::= { linkTable 1 }

  LinkEntry ::=
    SEQUENCE {
      linkLineIndex          LineIndex,
      linkWireStatus         INTEGER,
      linkYellowFormat       INTEGER,
      linkYellowForce        INTEGER,
      linkRxEqualizer        INTEGER,
      linkSignalling         INTEGER,
      linkLineBuildOut       INTEGER,
      linkInjectError        INTEGER,
      linkIsdnSwitchType     INTEGER,
      linkNfasInterfaceId    INTEGER,
      linkNfasPrimaryPointer INTEGER,
      linkSignalStatus       INTEGER,
      linkReceiveSensitivity INTEGER,
      linkReceiveQuality     INTEGER
    }

  linkLineIndex OBJECT-TYPE
    SYNTAX  LineIndex
    ACCESS  read-only
    STATUS  mandatory
    DESCRIPTION
                "This object is the identifier of an entry in
                the Enterprise DS1  MIB.  This will coorilate
                with the identifier used on the Standar DS1 MIB."
    ::= { linkEntry 1 }


  linkWireStatus OBJECT-TYPE
    SYNTAX  INTEGER {
      linkOK(0),
      linkTxShort(1),
      linkTxOpen(2)
      }
    ACCESS      read-only
    STATUS  mandatory
    DESCRIPTION
                "This variable provides error condition information
                on the Link."
    ::= { linkEntry 2 }

  linkYellowFormat OBJECT-TYPE
    SYNTAX  INTEGER {
      linkYellowFormatBit2(1),
      linkYellowFormatDL(2),
      linkYellowFormatFrame12FS(3)
      }
    ACCESS      read-write
    STATUS  mandatory
    DESCRIPTION
                "This variable identifies which standard will be used to
                transmit and identify the Yellow Alarm.
                YellowFormatBit2:      Bit-2 equal zero in every channel
                YellowFormatDL:        FF00 pattern in the Data Link
                YellowFormatFrame12FS: FS bit of frame 12"
    ::= { linkEntry 3 }

  linkYellowForce OBJECT-TYPE
    SYNTAX  INTEGER {
      linkYellowAuto(1),
      linkYellowOn(2),
      linkYellowDisable(3)
      }
    ACCESS      read-write
    STATUS  mandatory
    DESCRIPTION
                "This variable identifies which standard will be used to
                transmit and identify the Yellow Alarm.
                YellowOff
                  Do NOT force the transmission of a yellow alarm.  But,
                  yellow alarm may be automatically transmitted.
                YellowOn
                  Force the transmission of a yellow alarm even if the received
                  signal is in frame.
                YellowDisable
                  Do NOT transmit a yellow alarm even if the received signal is
                  out of frame."
    ::= { linkEntry 4 }

  linkRxEqualizer OBJECT-TYPE
    SYNTAX  INTEGER {
      linkRxEqualizerOff(1),
      linkRxEqualizerOn(2)
      }
    ACCESS      read-write
    STATUS  mandatory
    DESCRIPTION
                "This variable determines the equualization used on the
                received signal.  Long haul signals should have the
                equalization set for more.  Short haul signals require less
                equalization."
    ::= { linkEntry 5 }

  linkSignalling OBJECT-TYPE
    SYNTAX  INTEGER {
      linkGroundStart(1),
      linkLoopStart(2),
      linkOfficeGroundStart(3),
      linkOfficeLoopStart(4),
      linkEMWinkStart(6),
      linkEMImmediateStart(7),
      linkTiawanR1(8)
      }
    ACCESS  read-write
    STATUS  mandatory
    DESCRIPTION
                "This variable determines which robbed bit signalling
                technique is used.  The techniques designated OFFICE are
                used to simulate the central office site.  These allow
                back to back connections."
    ::= { linkEntry 6 }

  linkLineBuildOut OBJECT-TYPE
    SYNTAX  INTEGER {
      triState(0),
      e1pulse(1),
      t1pulse0dB(2),
      t1pulse-7dB(3),
      t1pulse-15dB(4)
      }
    ACCESS      read-write
    STATUS  mandatory
    DESCRIPTION
                "This variable is used in T1 applications to adjust the
                T1 pulse shape at the cross connect point.  The user
                should select the enumeration which best represents the
                amount of cable between the unit and the cross connect
                point"
    ::= { linkEntry 7 }

  linkInjectError OBJECT-TYPE
    SYNTAX  INTEGER {
      noErrorInjection(0),
      injectCRCerrorBurst(1),
      injectLineErrorBurst(2)
      }
    ACCESS  read-write
    STATUS  mandatory
    DESCRIPTION
                "This object is not a settable variable but rather a
                one shot.  Each time the variable is set to an error
                injection option then one burst of that error is
                forced on the line.  The exact number is error events
                on the line is not determined.  Use this variable to
                test that the far end properly monitoring faults."
    ::= { linkEntry 8 }


  linkIsdnSwitchType OBJECT-TYPE
    SYNTAX  INTEGER {
      ni1(0),
      dms(1),
      att(2),
      ctr4(3),
      ts014(4),
      ins1500(5),
      ctr4lapdonly(6),
      nfasSlave(7),
      ni1-NT(8),
      dms-NT(9),
      att-NT(10),
      ctr4-NT(11),
      ts014-NT(12),
      ins1500-NT(13)
      }
    ACCESS  read-write
    STATUS  mandatory
    DESCRIPTION "This object allows the selection of the ISDN variations
                 on the ISDN protocol depending on the switch manufacture
                 which we are connected to.  The nfasSlave selection turns
                 the D-channel off and attaches to the pointed to primary."
    ::= { linkEntry 9 }

  linkNfasInterfaceId OBJECT-TYPE
    SYNTAX  INTEGER (0..31)
    ACCESS  read-write
    STATUS  mandatory
    DESCRIPTION "When the linkIsdnSwitchType is set to nfasSlave then this
                 object defines the interface identifier that this interface
                 will be known as.  This must coorispond to the id as passed
                 in the Channel Identification element in the ISDN packet.
                 This should be a unique number within the NFAS group, provided
                 by the telco."
    ::= { linkEntry 10 }


  linkNfasPrimaryPointer OBJECT-TYPE
    SYNTAX  INTEGER (1..256)
    ACCESS  read-write
    STATUS  mandatory
    DESCRIPTION "When the linkIsdnSwitchType is set to nfasSlave then this
                 object defines the WAN port that will act as the D-channel
                 for this WAN port."
    ::= { linkEntry 11 }

  linkSignalStatus OBJECT-TYPE
    SYNTAX  INTEGER (1..8191)
    ACCESS  read-write
    STATUS  mandatory
    DESCRIPTION
                "This variable indicates the Signal Status of the
                interface.

     The linkSignalStatus is a bit  map  represented  as  a  sum,
     therefore, it can represent multiple failures (alarms) and
     a LoopbackState simultaneously.

     dsx1NoAlarm should be set if and only if no other flag  is
     set.

     If the dsx1LoopbackState bit is set, the loopback  in  ef-
     fect can be determined from the dsx1LoopbackConfig object.

     The various bit positions are:
          1     SingalNoAlarm           No Alarm Present"
    ::= { linkEntry 12 }


  linkReceiveSensitivity OBJECT-TYPE
    SYNTAX  INTEGER {
      linkSensitivityLevel1(1),
      linkSensitivityLevel2(2),
      linkSensitivityLevel3(3),
      linkSensitivityLevel4(4),
      linkSensitivityLevel5(5),
      linkSensitivityLevel6(6),
      linkSensitivityLevel7(7)
      }
    ACCESS  read-write
    STATUS  mandatory
    DESCRIPTION "This object allows the selection of the receiver
                 sensitivity on the WAN ports. In the voltage falls
                 below the sensitivity level a LOS will be specified.
                 This valiable is only valid if the linkRxEqualizer 
                 is set to ON"
    ::= { linkEntry 13 }

  linkReceiveQuality OBJECT-TYPE
    SYNTAX  INTEGER {
      dB0(0),
      dB1-7(1),
      dB3-4(2),
      dB5-1(3),
      dB6-8(4),
      dB8-5(5),
      dB10-2(6),
      dB11-9(7),
      dB13-6(8),
      dB15-3(9),
      dB17(10),
      dB18-7(11),
      dB20-4(12),
      dB22-1(13),
      dB23-8(14),
      dB25-5(15),
      dB27-2(16),
      dB28-9(17),
      dB30-6(18),
      dB32-3(19),
      dB34(20),
      dB35-7(21),
      dB37-4(22),
      dB39-1(23),
      dB40-8(24),
      dB42-5(25),
      notApplicable(30),
      adapting(31),
      valid(32),
      invalid(33),
      validWithNoise(34)
      }
    ACCESS  read-only
    STATUS  mandatory
    DESCRIPTION "This read-only variable defines the received signal strength
                 and attenuation in the cable"
    ::= { linkEntry 14 }

  --*************************************************************************
  --*************************************************************************
  -- Define a channel oriented selection of functionality.
  channelTable OBJECT-TYPE
    SYNTAX      SEQUENCE OF ChannelEntry
    ACCESS      not-accessible
    STATUS      mandatory
    DESCRIPTION "Time channel function selection table"
    ::= { listener 2 }

  channelEntry OBJECT-TYPE
    SYNTAX      ChannelEntry
    ACCESS      not-accessible
    STATUS      mandatory
    DESCRIPTION "An entry in the time channel selection table."
    INDEX   { linkLineIndex, channelIndex }
    ::= { channelTable 1 }

  ChannelEntry ::=
    SEQUENCE {
      channelIndex    INTEGER,
      channelFunction INTEGER,
      channelState    INTEGER
    }

  channelIndex OBJECT-TYPE
    SYNTAX      INTEGER (1..30)
    ACCESS      read-only
    STATUS      mandatory
    DESCRIPTION "This object is the identifier of an entry in
                 the channel table."
    ::= { channelEntry 1 }

  channelFunction OBJECT-TYPE
    SYNTAX  INTEGER {
      off(0),
      dialin(1),
      dialout(2),
      frameRelay(3),
      privateLine(4),
      ppp(5),
      dropinsert(7),
      blocked(8),
      clear(9)
      }
    ACCESS      read-write
    STATUS      mandatory
    DESCRIPTION ""
    ::= { channelEntry 2 }

  channelState OBJECT-TYPE
    SYNTAX  INTEGER {
      off(0),
      idle(1),
      active(2),
      frameRelay(3),
      clear(4),
      privateLineWait(5),
      privateLineActive(6),
      ppp(7),
      adminBlocked(10),
      resourceBlocked(11),
      telcoBlocked(12),
      dChannel(13)
      }
    ACCESS      read-only
    STATUS      mandatory
    DESCRIPTION ""
    ::= { channelEntry 3 }


  --*************************************************************************
  --*************************************************************************
  --
  --*************************************************************************
  --*************************************************************************
  dsx1LocalConfigTable OBJECT-TYPE
    SYNTAX  SEQUENCE OF Dsx1LocalConfigEntry
    ACCESS  not-accessible
    STATUS  mandatory
    DESCRIPTION
      "This is a virtual extension of the DS1 Configuration 
		  table implimented so that we can access some of 
		  dsx1 information without adding it to rfc1406."
    ::= { listener 3 }


  dsx1LocalConfigEntry OBJECT-TYPE
    SYNTAX  Dsx1LocalConfigEntry
    ACCESS  not-accessible
    STATUS  mandatory
    DESCRIPTION
      "An entry in the DS1 Virtual Configuration table."
    INDEX   { dsx1LocalLineIndex }
    ::= { dsx1LocalConfigTable 1 }

  Dsx1LocalConfigEntry ::=
    SEQUENCE {
         dsx1LocalLineIndex
             INTEGER,
         dsx1LocalLineStatus
             INTEGER
    }

  dsx1LocalLineIndex OBJECT-TYPE
    SYNTAX  INTEGER (1..'7fffffff'h)
    ACCESS  read-only
    STATUS  mandatory
    DESCRIPTION
        "This object is the identifier of a DS1  Inter-
        face on a managed device.  If there is an ifEn-
        try that is directly associated with  this  and
        only  this  DS1  interface,  it should have the
        same value as ifIndex.   Otherwise,  the  value
        exceeds  ifNumber,  and  is a unique identifier
        following this rule: inside  interfaces  (e.g.,
        equipment  side)  with even numbers and outside
        interfaces  (e.g.,  network   side)   with   odd
        numbers."
   ::= { dsx1LocalConfigEntry 1 }


  dsx1LocalLineStatus OBJECT-TYPE
    SYNTAX  INTEGER {
         off(0),
         on(1),
         down(2)
         }
    ACCESS  read-only
    STATUS  mandatory
    DESCRIPTION
        "This is a entry into the dsx1 information the 
		    will give a merge of the Line Type and Line Status
		    inorder to report a general condition of the line.
		    off(0)  - The link is not configured
		    on(1)   - The link is connected without errors
		    down(2) - The link is configured, but in error"
   ::= { dsx1LocalConfigEntry 100 }


  --*************************************************************************
  --*************************************************************************
  --                                 Dial In
  --*************************************************************************
  --*************************************************************************

 diIpPool OBJECT-TYPE
    SYNTAX      IpPool
    ACCESS      read-write
    STATUS      mandatory
    DESCRIPTION "String describing the IP address pool."
    ::= { calldialin 1 }

  diLoginTechnique OBJECT-TYPE
    SYNTAX      LoginTechnique
    ACCESS      read-write
    STATUS      mandatory
    DESCRIPTION "This variable defines the login sequence that a dial-up
                user will see.  The various options are defined below:

                Text or PAP
                A Username prompt is displayed. The received data is 
                monitored for PPP content.  If the received data looks 
                like PPP packets then PAP authentication will be done.
                If the received data looks like a username then a normal
                querryText login will continue;

                Text or CHAP or PAP
                A Username prompt is displayed. The received data is 
                monitored for PPP content.  If the received data looks 
                like PPP packets then CHAP or PAP authentication will be done.
                If the received data looks like a username then a normal
                querryText login will continue;

                Text
                A Username prompt is displayed and a username must be entered.
                If the received username is a static user with no password
                defined then the connection completes and no password prompt.
                Otherwise a password prompt is displayed and a password must
                be entered.

                PAP
                This setting assumes that all calls will be PPP users.  No
                username or password prompt will be displayed.  The system
                will go directly to PPP processing.  The dial-up user
                must be configured for PAP authentication.

                CHAP
                This setting assumes that all calls will be PPP users.  No
                username or password prompt will be displayed.  The system
                will go directly to PPP processing.  The dial-up user
                must be configured for CHAP authentication.

                CHAP or PAP
                This setting assumes that all calls will be PPP users.  No
                username or password prompt will be displayed.  The system
                will go directly to PPP processing.  The dial-up user
                must be configured for CHAP or PAP authentication."
    ::= { calldialin 2 }

  diUsernamePrompt OBJECT-TYPE
    SYNTAX      DisplayString (SIZE (0..39))
    ACCESS      read-write
    STATUS      mandatory
    DESCRIPTION "This defines the character string that will be displayed
                at user authentication time to request the users name.
                This should be a ASCII printable string and can include
                charrage returns and line feeds."
    ::= { calldialin 3 }

  diPasswordPrompt OBJECT-TYPE
    SYNTAX      DisplayString (SIZE (0..39))
    ACCESS      read-write
    STATUS      mandatory
    DESCRIPTION "This defines the character string that will be displayed
                at user authentication time to request the users password.
                This should be a ASCII printable string and can include
                charrage returns and line feeds."
    ::= { calldialin 4 }

  diBanner OBJECT-TYPE
    SYNTAX      DisplayString (SIZE (0..254))
    ACCESS      read-write
    STATUS      mandatory
    DESCRIPTION "A string to initially display for the user."
    ::= { calldialin 5 }

  diService OBJECT-TYPE
    SYNTAX      INTEGER {
                  rlogin(1),
                  telnet(2),
                  tcpraw(3),
                  ppp(4),
                  slip(5),
                  vpn(6)
                }
    ACCESS      read-write
    STATUS      mandatory
    DESCRIPTION "This object defines the default service that will be
                provided if the authentication technique does not
                specifically provide a service type."
    ::= { calldialin 6 }

  diServiceIP OBJECT-TYPE
    SYNTAX      IpAddress
    ACCESS      read-write
    STATUS      mandatory
    DESCRIPTION "This object defines the IP address which will be used
                for login connections (telnet,rlogin,vpn) when the authentication
                technique has not specifically provided an IP address to
                connect to."
    ::= { calldialin 7 }

  diPrimaryDNS OBJECT-TYPE
    SYNTAX      IpAddress
    ACCESS      read-write
    STATUS      mandatory
    DESCRIPTION "The primary domain name server address to
                 pass to the caller (Win95 PPP)."
    ::= { calldialin 8 }

  diSecondaryDNS OBJECT-TYPE
    SYNTAX      IpAddress
    ACCESS      read-write
    STATUS      mandatory
    DESCRIPTION "The secondary domain name server address to
                 pass to the caller (Win95 PPP)."
    ::= { calldialin 9 }

  diPrimaryWINS OBJECT-TYPE
    SYNTAX      IpAddress
    ACCESS      read-write
    STATUS      mandatory
    DESCRIPTION "The primary Windows name server address to
                 pass to the caller (Win95 PPP)."
    ::= { calldialin 10 }

  diSecondaryWINS OBJECT-TYPE
    SYNTAX      IpAddress
    ACCESS      read-write
    STATUS      mandatory
    DESCRIPTION "The secondary Windows name server address to
                 pass to the caller (Win95 PPP)."
    ::= { calldialin 11 }

  diFailureBanner OBJECT-TYPE
    SYNTAX      DisplayString (SIZE (0..254))
    ACCESS      read-write
    STATUS      mandatory
    DESCRIPTION "This defines a message that will be displayed to a
                user when authentication failed.  This is only
                relevant when the authentication technique was Text."
    ::= { calldialin 12 }

  diAllowAttempts OBJECT-TYPE
    SYNTAX      INTEGER
    ACCESS      read-write
    STATUS      mandatory
    DESCRIPTION "The maximum number of attempts a user will be given to
                login before being disconnected.  This applies to Text
                authentications only.  PAP and CHAP authentications are
                only allowed a single attempt."
    ::= { calldialin 13 }

  diLinkCompression OBJECT-TYPE
    SYNTAX      EnabledDisabled
    ACCESS      read-write
    STATUS      mandatory
    DESCRIPTION "This object enables the PPP link layer address and
                protocol field compression.  When enabled the PPP
                negotiations will DESIRE link compression but may disable
                the compression due the other end of the link.  When
                disabled the PPP negotiations will FORCE no compression
                on the PPP link.

                This is a default setting which may be overridden by
                the authentication of a specific user."
    ::= { calldialin 14 }

  diConfigInitialMRU OBJECT-TYPE
    SYNTAX      INTEGER
    ACCESS      read-write
    STATUS      mandatory
    DESCRIPTION "Default setting for Maximum Receive
                 Unit (MRU) if it's not changed by
                 authentication or PPP."
    ::= { calldialin 15 }

  diServicePort OBJECT-TYPE
    SYNTAX      INTEGER
    ACCESS      read-write
    STATUS      mandatory
    DESCRIPTION "This object defines the IP port number which will be used
                for login connections (telnet,rlogin,vpn) when the authentication
                technique has not specifically provided a port number to
                connect to.

                If no TCP/UDP port number is specifically provided then the 
                UNIX defaults will be used:
                         telnet   23
                         rlogin   513
                         l2tp     1701"
    ::= { calldialin 16 }

  diTotalCallAttempts OBJECT-TYPE
    SYNTAX      INTEGER
    ACCESS      read-write
    STATUS      mandatory
    DESCRIPTION "The total number of calls which have been attempted since
                 the last boot of the box."
    ::= { calldialin 17 }

  diConfigMagicNumber OBJECT-TYPE
    SYNTAX      INTEGER {
                  enable(1),
                  disable(2)
                }
    ACCESS      read-write
    STATUS      mandatory
    DESCRIPTION "Determines if magic number negotiation should be done."
    ::= { calldialin 18 }

  diConfigFcsSize OBJECT-TYPE
    SYNTAX      INTEGER
    ACCESS      read-write
    STATUS      mandatory
    DESCRIPTION "The size of the FCS, in bits, the local node
                 will attempt to negotiate for use with the
                 remote node."
    ::= { calldialin 19 }

  diIpConfigCompression OBJECT-TYPE
    SYNTAX      IpConfigCompression
    ACCESS      read-write
    STATUS      mandatory
    DESCRIPTION "If none(1) then the local node will not
                 attempt to negotiate any IP Compression option.
                 Otherwise, the local node will attempt to
                 negotiate compression mode indicated by the
                 enumerated value. Changing this object will
                 have effect when the link is next restarted."
    REFERENCE   "Section 4.0, Van Jacobson TCP/IP Header
                 Compression of RFC1332."

    ::= { calldialin 20 }

  diSessionTimeout OBJECT-TYPE
    SYNTAX      INTEGER
    ACCESS      read-write
    STATUS      mandatory
    DESCRIPTION "This is the maximum time in minutes which a connection
                is allowed to be maintained.  After this time the connection
                will be terminated, even if there is acive traffic on the
                connection.

                This is a default setting which may be overridden by
                the authentication of a specific user."
    ::= { calldialin 21 }

  diIdleTimeout OBJECT-TYPE
    SYNTAX      INTEGER
    ACCESS      read-write
    STATUS      mandatory
    DESCRIPTION "This is the maximum time in minutes which a connection
                is allowed to be maintained with no traffic.  After this
                time, if no traffic is seen, the connection will be
                terminated.

                This is a default setting which may be overridden by
                the authentication of a specific user."
    ::= { calldialin 22 }

  diLoginTimeout OBJECT-TYPE
    SYNTAX      INTEGER
    ACCESS      read-write
    STATUS      mandatory
    DESCRIPTION "This is the maximum time in seconds which a user is given
                to login.  This is only relevant before the user is
                authenticated.  This setting should take into account any
                time required to querry a remote authentication server
                (ie. RADIUS)."
    ::= { calldialin 23 }

  diLingerTime OBJECT-TYPE
    SYNTAX      INTEGER
    ACCESS      read-write
    STATUS      mandatory
    DESCRIPTION "Number of seconds a MIB entry in the Active
                 table will remain after the call is dead."
    ::= { calldialin 24 }

  diActive OBJECT-TYPE
    SYNTAX      INTEGER
    ACCESS      read-write
    STATUS      mandatory
    DESCRIPTION "The total number of active calls."
    ::= { calldialin 25 }

--***************************************************
-- Modulation enable

  diModemV90Enable OBJECT-TYPE
    SYNTAX      INTEGER {
      disable(0),
      enable(1)
      }
    ACCESS      read-write
    STATUS      mandatory
    DESCRIPTION "Allow V90 modulation"
    ::= { calldialin 50 }

  diModemK56Enable OBJECT-TYPE
    SYNTAX      INTEGER {
      disable(0),
      enable(1)
      }
    ACCESS      read-write
    STATUS      mandatory
    DESCRIPTION "Allow K56Flex modulation"
    ::= { calldialin 51 }

  diModemV34Enable OBJECT-TYPE
    SYNTAX      INTEGER {
      disable(0),
      enable(1)
      }
    ACCESS      read-write
    STATUS      mandatory
    DESCRIPTION "Allow V34 and V34 annex 12 modulations"
    ::= { calldialin 26 }

  diModemV32Enable OBJECT-TYPE
    SYNTAX  INTEGER {
      disable(0),
      enable(1)
      }
    ACCESS      read-write
    STATUS      mandatory
    DESCRIPTION "Allow V32 and V32bis modulations"
    ::= { calldialin 27 }

  diModemV23Enable OBJECT-TYPE
    SYNTAX      INTEGER {
      disable(0),
      enable(1)
      }
    ACCESS      read-write
    STATUS      mandatory
    DESCRIPTION "Allow V23 modulation"
    ::= { calldialin 52 }

  diModemV22Enable OBJECT-TYPE
    SYNTAX      INTEGER {
      disable(0),
      enableV22(1),
      enableBell212(2)
      }
    ACCESS      read-write
    STATUS      mandatory
    DESCRIPTION "Allow V22 or Bell 212 modulations"
    ::= { calldialin 28 }

  diModemV21Enable OBJECT-TYPE
    SYNTAX      INTEGER {
      disable(0),
      enableV21(1),
      enableBell103(2)
      }
    ACCESS      read-write
    STATUS      mandatory
    DESCRIPTION "Allow V21 or Bell 103 modulations"
    ::= { calldialin 29 }

  diModemMaxSpeed OBJECT-TYPE
    SYNTAX      INTEGER
    ACCESS      read-write
    STATUS      mandatory
    DESCRIPTION "This variable allows the selection of the fastest
                 data rate that will be negotiated."
    ::= { calldialin 30 }

  diModemMinSpeed OBJECT-TYPE
    SYNTAX      INTEGER
    ACCESS      read-write
    STATUS      mandatory
    DESCRIPTION "This variable allows the selection of the slowest
                 data rate that will be negotiated."
    ::= { calldialin 31 }

  diModemGuardTone OBJECT-TYPE
    SYNTAX  INTEGER {
      toneNone(1),
      tone1800(3)
      }
    ACCESS      read-write
    STATUS      mandatory
    DESCRIPTION "Normally a guard tone is not required.  But, one can be
                 inserted.  This operates for Phase Shift Key modulations only."
    ::= { calldialin 32 }

  diModemCarrierLossDuration OBJECT-TYPE
    SYNTAX      INTEGER (1..255)
    ACCESS      read-write
    STATUS      mandatory
    DESCRIPTION "The number of seconds the carrier must be 
                 lost before it is considered the connection dead. A
                 setting above 100 indicates forever."
    ::= { calldialin 33 }

  diModemRetrain OBJECT-TYPE
    SYNTAX      INTEGER {
      none(0),
      retrain(1),
      fallForwardFallBack(2)
      }
    ACCESS      read-write
    STATUS      mandatory
    DESCRIPTION "Allow the modem to monitor the line quality and 
                 request a fallback or retrain for poor quality and a
                 fallforward for good quality."
    ::= { calldialin 34 }

  diModemTxLevel OBJECT-TYPE
    SYNTAX      INTEGER (0..15)
    ACCESS      read-write
    STATUS      mandatory
    DESCRIPTION "This variable should be set with caution; and normally
                 only after talking to a factory representative.  This
                 sets the transmit level power level of the modem.  The
                 scale is 0 (0 dB) to 15 (-15 dB).   Note that larger
                 numbers mean less power."
    ::= { calldialin 35 }

  diModemProtocol OBJECT-TYPE
    SYNTAX      INTEGER {
      direct(0),
      requestV42(1),
      requireV42(2)
      }
    ACCESS      read-write
    STATUS      mandatory
    DESCRIPTION "Selection of the data protocol to use on the modem.
                 This allows the request of or forcing of V42
                 error correction protocol."
    ::= { calldialin 36 }

  diModemCompression OBJECT-TYPE
    SYNTAX      INTEGER {
      direct(0),
      requestV42bis(1),
      requireV42bis(2),
      v44(3)
      }
    ACCESS      read-write
    STATUS      mandatory
    DESCRIPTION "Selection of the data compression protocol to use on 
                 the modem. This allows the request of or forcing of 
                 V42 compression protocol.  This will only be 
                 used if V42 error correction is active."
    ::= { calldialin 37 }

  diModemBillingDelay OBJECT-TYPE
    SYNTAX      INTEGER (0..2)
    ACCESS      read-write
    STATUS      mandatory
    DESCRIPTION "The number of seconds after answering the call during
                 which the modem should remain silent.  On older phone
                 systems the silence time was required to allow billing
                 tones to pass."
    ::= { calldialin 38 }

  diMaxActive OBJECT-TYPE
    SYNTAX      INTEGER
    ACCESS      read-write
    STATUS      mandatory
    DESCRIPTION "The maximum number of active calls seen at one time."
    ::= { calldialin 39 }

  diSuccessBanner OBJECT-TYPE
    SYNTAX      DisplayString (SIZE (0..254))
    ACCESS      read-write
    STATUS      mandatory
    DESCRIPTION "This defines a message that will be displayed to a
                user when authentication was successful.  This will only be
                displayed in the case of a text login.  There are the
                following special characters which can be inserted in this 
                string to cause the run time insertion of live data:
                  \r    carriage return
                  \n    new line
                  \I    the users IP address in the form 1.2.3.4
                  \M    the users MTU"
    ::= { calldialin 40 }

  diConfigMultiLink OBJECT-TYPE
    SYNTAX      INTEGER
    ACCESS      read-write
    STATUS      mandatory
    DESCRIPTION "Maximum multilink calls per user; 0 disables multilink."
    ::= { calldialin 41 }

  diConfigMMP OBJECT-TYPE
    SYNTAX  INTEGER {
      disable(0),
      enable(1)
      }
    ACCESS      read-write
    STATUS      mandatory
    DESCRIPTION "This object enables MultiBox MultiLink Protocol.
                This should only be enabled if Multilink is enabled.
                When diConfigMMP is enabled, multilink calls over 
                multiple RAS boxes will be bundled together.  This
                would be necessary in an environment where a single
                multilink call could physically be distributed over
                different T1's."
    ::= { calldialin 42 }

  diForceNextHop OBJECT-TYPE
    SYNTAX      IpAddress
    ACCESS      read-write
    STATUS      mandatory
    DESCRIPTION "Provides a default value for the dactForceNextHop
                 parameter of each active call.  This can be overridden
                 by using RADIUS attribute 209"
    ::= { calldialin 43 }

  diPageSort OBJECT-TYPE
    SYNTAX      INTEGER{
                descending(0),
                ascending(1)
                }			
    ACCESS      read-write
    STATUS      mandatory
    DESCRIPTION "sorts calls on dial-in page
				 0 - most recent calls at bottom
				 1 - most recent calls at top"
    ::= { calldialin 44 }

  --***************
  -- V.92 features
  --***************

  diModemV92Enable OBJECT-TYPE
    SYNTAX      INTEGER {
      disable(0),
      enable(1)
      }
    ACCESS      read-write
    STATUS      mandatory
    DESCRIPTION "Allow V92 modulations"
    ::= { calldialin 45 }

  diV92QuickConnect OBJECT-TYPE
    SYNTAX      INTEGER {
      disable(0),
      enable(1)
      }
    ACCESS      read-write
    STATUS      mandatory
    DESCRIPTION "Allow V92 Quick Connect"
    ::= { calldialin 46 }

  diV92ModemOnHold OBJECT-TYPE
    SYNTAX      INTEGER {
      disable(0),
      enable(1)
      }
    ACCESS      read-write
    STATUS      mandatory
    DESCRIPTION "Allow V92 Modem on Hold"
    ::= { calldialin 47 }

  diV92ModemOnHoldTimeout OBJECT-TYPE
    SYNTAX      INTEGER {
      disabled(0),
      ten-sec(1),
      twenty-sec(2),
      thirty-sec(3),
      forty-sec(4),
      one-min(5),
      two-min(6),
      three-min(7),
      four-min(8),
      six-min(9),
      eight-min(10),
      twelve-min(11),
      sixteen-min(12),
      never(13)
      }
    ACCESS      read-write
    STATUS      mandatory
    DESCRIPTION "v.92 modem on hold timeout period"
    ::= { calldialin 48 }

  diV59Enable OBJECT-TYPE
    SYNTAX      INTEGER {
      disable(0),
      enable(1)
      }
    ACCESS      read-write
    STATUS      mandatory
    DESCRIPTION "Enables the sending of V.59 messages to the 
                 radius server."
    ::= { calldialin 49 }

  diModemAnswerToneLength OBJECT-TYPE
    SYNTAX      INTEGER
    ACCESS      read-write
    STATUS      mandatory
    DESCRIPTION "This is the Answer tone length for low speed modems.
                If only modulations below v.34 are enabled, the tone length
                can be reduced to a minimum of 1 millisecond which will reduce
                the total time it takes for the modem to connect."
    ::= { calldialin 56 }

-- V.110 stuff

  diV110Enable OBJECT-TYPE
    SYNTAX      INTEGER {
      disable(0),
      enable(1)
      }
    ACCESS      read-write
    STATUS      mandatory
    DESCRIPTION "Enable the detection of v.110"
    ::= { calldialin 53 }

-- Leased Line stuff


  diModemMaxV8Failures OBJECT-TYPE
    SYNTAX      INTEGER
    ACCESS      read-write
    STATUS      mandatory
    DESCRIPTION "The max number of V8 modem failures allowed."
    ::= { calldialin 55 }

  diCallbackConfig OBJECT-TYPE
    SYNTAX      INTEGER {
      noCallback(0),
      setByAuth(1),
      setByCaller(2),
      callingNum(3)
      }
    ACCESS      read-write
    STATUS      mandatory
    DESCRIPTION "Globally enable/disable callback"
    ::= { calldialin 57 }
    
  diSecServiceIP OBJECT-TYPE
    SYNTAX      IpAddress
    ACCESS      read-write
    STATUS      mandatory
    DESCRIPTION "This object defines the secondary IP address which will be used
                for login connections (telnet,rlogin,vpn) when the authentication
                technique has not specifically provided an IP address to
                connect to.  This IP address will be used if the default connection
                cannot be established."
    ::= { calldialin 58 }
    
  diSecServicePort OBJECT-TYPE
    SYNTAX      INTEGER
    ACCESS      read-write
    STATUS      mandatory
    DESCRIPTION "This object defines the Secondary IP port number which will be used
                for login connections (telnet,rlogin,vpn) if the default connection
                cannot be established.

                If no TCP/UDP port number is specifically provided then the 
                UNIX defaults will be used:
                         telnet   23
                         rlogin   513
                         l2tp     1701"
    ::= { calldialin 59 }

  diServiceTimeout OBJECT-TYPE
    SYNTAX      INTEGER
    ACCESS      read-write
    STATUS      mandatory
    DESCRIPTION "This is the maximum time in seconds that the server will try
                 to establish a tcp connection.  After this timeout, the server
                 will try the secondary address if specified and start a new timer
                 with this value."
    ::= { calldialin 60 }

  --*************************************************************************
  -- Table of individual active calls

  diactTable OBJECT-TYPE
    SYNTAX      SEQUENCE OF DiactEntry
    ACCESS      not-accessible
    STATUS      mandatory
    DESCRIPTION "Table of individual active calls."
    ::= { calldialin 100 }

  diactEntry OBJECT-TYPE
    SYNTAX       DiactEntry
    ACCESS       not-accessible
    STATUS       mandatory
    DESCRIPTION  "An entry of an active call."
    INDEX        { diactIndex }
    ::= { diactTable 1 }

  DiactEntry ::=
    SEQUENCE {
      diactIndex                  Index,
      diactMultiIndex             INTEGER,
      diactState                  DialinState,
      diactProtocol               INTEGER,
      diactAccessLevel            AccessLevel,
      diactDSPIndex               INTEGER,
      diactIFIndex                INTEGER,
      diactLinkIndex              INTEGER,
      diactSlotIndex              INTEGER,
      diactIP                     IpAddress,
      diactPort                   INTEGER,
      diStatBadAddresses          INTEGER,
      diStatBadControls           Counter,
      diStatPacketTooLongs        Counter,
      diStatBadFCSs               Counter,
      diStatLocalMRU              INTEGER,
      diStatRemoteMRU             INTEGER,
      diStatLocalToPeerACCMap     OCTET STRING,
      diStatPeerToLocalACCMap     OCTET STRING,
      diStatLocalToRemoteProtComp EnabledDisabled,
      diStatRemoteToLocalProtComp EnabledDisabled,
      diStatLocalToRemoteACComp   EnabledDisabled,
      diStatRemoteToLocalACComp   EnabledDisabled,
      diStatTransmitFcsSize       FcsSize,
      diStatReceiveFcsSize        FcsSize,
      diIpOperStatus              INTEGER,
      diIpLocalToRemoteCompProt   IpConfigCompression,
      diIpRemoteToLocalCompProt   IpConfigCompression,
      diIpRemoteMaxSlotId         MaxSlotId,
      diIpLocalMaxSlotId          MaxSlotId,
      diactSessionTime            TimeTicks,
      diactRemainingIdle          INTEGER,
      diactRemainingSession       TimeTicks,
      diactNumberDialed           DialedNumber,
      diactCallingPhone           DisplayString,
      diactSentOctets             Counter,
      diactReceivedOctets         Counter,
      diactSentDataFrames         INTEGER,
      diactReceivedDataFrames     INTEGER,
      diactErrorFrames            INTEGER,
      diactSessionStartTime       TimeTicks,
      diactModulation             INTEGER,
      diactErrorCorrection        INTEGER,
      diactCompression            INTEGER,
      diactMultiLinkFlag          INTEGER,
      diactSymbolRate             INTEGER,
      diactTxSpeed                INTEGER,
      diactRxSpeed                INTEGER,
      diactUsername               DisplayString,
      diactPassword               DisplayString,
      diactTerminateReason        TerminateReason,
      diactTerminateState         DialinState,
      diactLocalRenegotiates      INTEGER,
      diactLocalRetrains          INTEGER,
      diactRemoteRenegotiates     INTEGER,
      diactRemoteRetrains         INTEGER,
      diStatLcpRemoteMRRU         INTEGER,
      diStatLcpLocalMRRU          INTEGER,
      diStatLcpAuth               LcpAuth,
      diStatIpFilterA             OCTET STRING,
      diStatIpFilterB             OCTET STRING,
      diStatIpFilterC             OCTET STRING,
      diStatIpFilterD             OCTET STRING,
      diStatIpFilterE             OCTET STRING,
      diStatIpFilterF             OCTET STRING,
      diStatIpFilterG             OCTET STRING,
      diStatIpFilterH             OCTET STRING,
      diStatIpFilterI             OCTET STRING,
      diStatIpFilterJ             OCTET STRING,
      diactForceNextHop           IpAddress,
      diactPrimaryDNS             IpAddress,
      diactSecondaryDNS           IpAddress
    }

  diactIndex OBJECT-TYPE
    SYNTAX      Index
    ACCESS      read-only
    STATUS      mandatory
    DESCRIPTION "Unique identification of this active call
                 (use linkTAble.linkTimeSlot.activeIndex)."
    ::= { diactEntry 1 }

  diactMultiIndex OBJECT-TYPE
    SYNTAX      INTEGER
    ACCESS      read-only
    STATUS      mandatory
    DESCRIPTION "Unique identification shared between
                 multilink active calls."
    ::= { diactEntry 2 }

  diactState OBJECT-TYPE
    SYNTAX      DialinState
    ACCESS      read-write
    STATUS      mandatory
    DESCRIPTION "Indicates current progress and reason for
                 termination."
    ::= { diactEntry 3 }

  diactProtocol OBJECT-TYPE
    SYNTAX      INTEGER {
                  ppp(1),
                  slip(2),
                  rlogin(3),
                  telnet(4),
                  tcpraw(5),
                  shell(6),
                  vpn(7)
                }
    ACCESS      read-only
    STATUS      mandatory
    DESCRIPTION "The service provided on this call."
    ::= { diactEntry 4 }

  diactAccessLevel OBJECT-TYPE
    SYNTAX      AccessLevel
    ACCESS      read-only
    STATUS      mandatory
    DESCRIPTION "The security level given to this call
                 (usually PASSTHRU)."
    ::= { diactEntry 5 }

  diactDSPIndex OBJECT-TYPE
    SYNTAX      INTEGER
    ACCESS      read-only
    STATUS      mandatory
    DESCRIPTION "Which DSP chip this call is on
                 (points to DSP table)."
    ::= { diactEntry 6 }

  diactIFIndex OBJECT-TYPE
    SYNTAX      INTEGER
    ACCESS      read-only
    STATUS      mandatory
    DESCRIPTION "Which interface this call is on
                 (points to the Interfaces table)."
    ::= { diactEntry 7 }

  diactLinkIndex OBJECT-TYPE
    SYNTAX      INTEGER
    ACCESS      read-only
    STATUS      mandatory
    DESCRIPTION "Which WAN link this call is on
                 (points to the Link table)."
    ::= { diactEntry 8 }

  diactSlotIndex OBJECT-TYPE
    SYNTAX      INTEGER
    ACCESS      read-only
    STATUS      mandatory
    DESCRIPTION "Which time slot this call is on
                 (points to the Fractional table)."
    ::= { diactEntry 9 }

  diactIP OBJECT-TYPE
    SYNTAX      IpAddress
    ACCESS      read-only
    STATUS      mandatory
    DESCRIPTION "The current IP address."
    ::= { diactEntry 10 }

  diactPort OBJECT-TYPE
    SYNTAX      INTEGER
    ACCESS      read-only
    STATUS      mandatory
    DESCRIPTION "The port number on a remote machine
                 (TELNET, RLOGIN, L2TP)."
    ::= { diactEntry 11 }

  diStatBadAddresses OBJECT-TYPE
    SYNTAX      INTEGER
    ACCESS      read-only
    STATUS      mandatory
    DESCRIPTION "Statistics on the link."
    ::= { diactEntry 12 }

  diStatBadControls OBJECT-TYPE
    SYNTAX      Counter
    ACCESS      read-only
    STATUS      mandatory
    DESCRIPTION "The number of packets received on this call
                 with an incorrect Control Field."
    ::= { diactEntry 13 }

  diStatPacketTooLongs OBJECT-TYPE
    SYNTAX      Counter
    ACCESS      read-only
    STATUS      mandatory
    DESCRIPTION "The number of received packets that have been
                 discarded because their length exceeded the
                 MRU."
    ::= { diactEntry 14 }

  diStatBadFCSs OBJECT-TYPE
    SYNTAX      Counter
    ACCESS      read-only
    STATUS      mandatory
    DESCRIPTION "The number of received packets that have been
                 discarded due to having an incorrect FCS."
    ::= { diactEntry 15 }

  diStatLocalMRU OBJECT-TYPE
    SYNTAX      INTEGER
    ACCESS      read-only
    STATUS      mandatory
    DESCRIPTION "The current value of the local Maximum Transfer
                 Unit (MRU) for PPP and SLIP."
    ::= { diactEntry 16 }

  diStatRemoteMRU OBJECT-TYPE
    SYNTAX      INTEGER
    ACCESS      read-only
    STATUS      mandatory
    DESCRIPTION "The current value of the remote Maximum Transfer
                 Unit (MRU) for PPP and SLIP."
    ::= { diactEntry 17 }

  diStatLocalToPeerACCMap OBJECT-TYPE
    SYNTAX      OCTET STRING
    ACCESS      read-only
    STATUS      mandatory
    DESCRIPTION "The current value of the ACC Map used for
                 sending packets from the local entity to
                 the remote entity."
    ::= { diactEntry 18 }

  diStatPeerToLocalACCMap OBJECT-TYPE
    SYNTAX      OCTET STRING
    ACCESS      read-only
    STATUS      mandatory
    DESCRIPTION "The current value of the ACC Map used for
                 sending packets from the remote entity to
                 the local entity."
    ::= { diactEntry 19 }

  diStatLocalToRemoteProtComp OBJECT-TYPE
    SYNTAX      EnabledDisabled
    ACCESS      read-only
    STATUS      mandatory
    DESCRIPTION "Indicates whether the local entity will
                 use Protocol Compression when transmitting
                 packets to the remote entity."
    ::= { diactEntry 20 }

  diStatRemoteToLocalProtComp OBJECT-TYPE
    SYNTAX      EnabledDisabled
    ACCESS      read-only
    STATUS      mandatory
    DESCRIPTION "Indicates whether the local entity will
                 use Protocol Compression when transmitting
                 packets to the remote entity."
    ::= { diactEntry 21 }

  diStatLocalToRemoteACComp OBJECT-TYPE
    SYNTAX      EnabledDisabled
    ACCESS      read-only
    STATUS      mandatory
    DESCRIPTION "Indicates whether the local entity will
                 use Address and Control Compression when
                 transmitting packets to the remote entity."
    ::= { diactEntry 22 }

  diStatRemoteToLocalACComp OBJECT-TYPE
    SYNTAX      EnabledDisabled
    ACCESS      read-only
    STATUS      mandatory
    DESCRIPTION "Indicates whether the remote entity will
                 use Address and Control Compression when
                 transmitting packets to the local entity."
    ::= { diactEntry 23 }

  diStatTransmitFcsSize OBJECT-TYPE
    SYNTAX      FcsSize
    ACCESS      read-only
    STATUS      mandatory
    DESCRIPTION "The size of the Frame Check Sequence (FCS) in
                 bits that the local node will generate when
                 sending packets to the remote node."
    ::= { diactEntry 24 }

  diStatReceiveFcsSize OBJECT-TYPE
    SYNTAX      FcsSize
    ACCESS      read-only
    STATUS      mandatory
    DESCRIPTION "The size of the Frame Check Sequence (FCS) in
                 bits that the local node will generate when
                 sending packets to the remote node."
    ::= { diactEntry 25 }

  diIpOperStatus OBJECT-TYPE
    SYNTAX      INTEGER
    ACCESS      read-only
    STATUS      mandatory
    DESCRIPTION "Operational status of the call."
    ::= { diactEntry 26 }

  diIpLocalToRemoteCompProt OBJECT-TYPE
    SYNTAX      IpConfigCompression
    ACCESS      read-only
    STATUS      mandatory
    DESCRIPTION "The IP compression protocol that the local
                 IP entity uses when sending packets to the
                 remote IP entity."
    ::= { diactEntry 27 }

  diIpRemoteToLocalCompProt OBJECT-TYPE
    SYNTAX      IpConfigCompression
    ACCESS      read-only
    STATUS      mandatory
    DESCRIPTION "The IP compression protocol that the remote
                 IP entity uses when sending packets to the
                 local IP entity."
    ::= { diactEntry 28 }

  diIpRemoteMaxSlotId OBJECT-TYPE
    SYNTAX      MaxSlotId
    ACCESS      read-only
    STATUS      mandatory
    DESCRIPTION "The Max-Slot-Id parameter that the remote node
                 has advertised and that is in use on the link.
                 If vj-tcp header compression is not in use on
                 the link then the value of this object shall be 0."
    ::= { diactEntry 29 }

  diIpLocalMaxSlotId OBJECT-TYPE
    SYNTAX      MaxSlotId
    ACCESS      read-only
    STATUS      mandatory
    DESCRIPTION "The Max-Slot-Id parameter that the local node
                 has advertised and that is in use on the link.
                 If vj-tcp header compression is not in use on
                 the link then the value of this object shall be 0."
    ::= { diactEntry 30 }

  diactSessionTime OBJECT-TYPE
    SYNTAX      TimeTicks
    ACCESS      read-only
    STATUS      mandatory
    DESCRIPTION "The number of seconds this call was/is active."
    ::= { diactEntry 31 }

  diactRemainingIdle OBJECT-TYPE
    SYNTAX      INTEGER
    ACCESS      read-only
    STATUS      mandatory
    DESCRIPTION "Number of minutes until idle timeout (counts down)."
    ::= { diactEntry 32 }

  diactRemainingSession OBJECT-TYPE
    SYNTAX      TimeTicks
    ACCESS      read-only
    STATUS      mandatory
    DESCRIPTION "Number of seconds left in this session (counts down)."
    ::= { diactEntry 33 }

  diactNumberDialed OBJECT-TYPE
    SYNTAX      DialedNumber
    ACCESS      read-only
    STATUS      mandatory
    DESCRIPTION "The phone number that was dialed into."
    ::= { diactEntry 34 }

  diactCallingPhone OBJECT-TYPE
    SYNTAX      DisplayString
    ACCESS      read-only
    STATUS      mandatory
    DESCRIPTION "The phone number that was dialed from."
    ::= { diactEntry 35 }

  diactSentOctets OBJECT-TYPE
    SYNTAX      Counter
    ACCESS      read-only
    STATUS      mandatory
    DESCRIPTION "The number of octets sent on this call."
    ::= { diactEntry 36 }

  diactReceivedOctets OBJECT-TYPE
    SYNTAX      Counter
    ACCESS      read-only
    STATUS      mandatory
    DESCRIPTION "The number of octets received on this call."
    ::= { diactEntry 37 }

  diactSentDataFrames OBJECT-TYPE
    SYNTAX      INTEGER
    ACCESS      read-only
    STATUS      mandatory
    DESCRIPTION "The number of sent packets on this call."
    ::= { diactEntry 38 }

  diactReceivedDataFrames OBJECT-TYPE
    SYNTAX      INTEGER
    ACCESS      read-only
    STATUS      mandatory
    DESCRIPTION "The number of received packets on this call."
    ::= { diactEntry 39 }

  diactErrorFrames OBJECT-TYPE
    SYNTAX      INTEGER
    ACCESS      read-only
    STATUS      mandatory
    DESCRIPTION "Number of bad received packets (CRC, Length,...)."
    ::= { diactEntry 40 }

  diactSessionStartTime OBJECT-TYPE
    SYNTAX      TimeTicks
    ACCESS      read-only
    STATUS      mandatory
    DESCRIPTION "The number of seconds this call was/is active."
    ::= { diactEntry 41 }

  diactModulation OBJECT-TYPE
    SYNTAX      ModemModulation
    ACCESS      read-only
    STATUS      mandatory
    DESCRIPTION "The modulation of the link."
    ::= { diactEntry 43 }

  diactErrorCorrection OBJECT-TYPE
    SYNTAX      INTEGER {
                  unknown(0),
                  none(1),
                  v42(2),
                  mnp(3),
                  v120(4),
                  cellular(5),
                  hdlc(6)
                }
    ACCESS      read-only
    STATUS      mandatory
    DESCRIPTION "The error correction scheme used on this call."
    ::= { diactEntry 44 }

  diactCompression OBJECT-TYPE
    SYNTAX      INTEGER {
                  unknown(0),
                  none(1),
                  v42bis(2),
                  mnp5(3),
                  stac(4),
                  v44(5)
                }
    ACCESS      read-only
    STATUS      mandatory
    DESCRIPTION "The compression technique used on this call."
    ::= { diactEntry 45 }

  diactMultiLinkFlag OBJECT-TYPE
    SYNTAX      INTEGER (0..1)
    ACCESS      read-only
    STATUS      mandatory
    DESCRIPTION "An indicator of whether this is a multilink
                 call or not.  0 is FALSE, 1 is TRUE."
    ::= { diactEntry 46 }

  diactSymbolRate OBJECT-TYPE
    SYNTAX      INTEGER
    ACCESS      read-only
    STATUS      mandatory
    DESCRIPTION "The symbol rate of the call (modem only)."
    ::= { diactEntry 48 }

  diactTxSpeed OBJECT-TYPE
    SYNTAX      INTEGER
    ACCESS      read-only
    STATUS      mandatory
    DESCRIPTION "The connected transmit-speed of the link."
    ::= { diactEntry 49 }

  diactRxSpeed OBJECT-TYPE
    SYNTAX      INTEGER
    ACCESS      read-only
    STATUS      mandatory
    DESCRIPTION "The connected receive-speed of the link."
    ::= { diactEntry 50 }

  diactUsername OBJECT-TYPE
    SYNTAX      DisplayString
    ACCESS      read-only
    STATUS      mandatory
    DESCRIPTION "The username that the caller entered."
    ::= { diactEntry 56 }

  diactPassword OBJECT-TYPE
    SYNTAX      DisplayString
    ACCESS      read-only
    STATUS      mandatory
    DESCRIPTION "The password that the caller entered."
    ::= { diactEntry 57 }

  diactTerminateReason OBJECT-TYPE
    SYNTAX      TerminateReason
    ACCESS      read-only
    STATUS      mandatory
    DESCRIPTION "The reason a call was disconnected."
    ::= { diactEntry 58 }

  diactTerminateState OBJECT-TYPE
    SYNTAX      DialinState
    ACCESS      read-write
    STATUS      mandatory
    DESCRIPTION "Indicates the value of diactState when the call was terminated"
    ::= { diactEntry 59 }

  diactLocalRenegotiates OBJECT-TYPE
    SYNTAX      INTEGER
    ACCESS      read-only
    STATUS      mandatory
    DESCRIPTION "The number of times the local side (this unit) has
                 initiated a modem speed renogotiate."
    ::= { diactEntry 60 }

  diactLocalRetrains OBJECT-TYPE
    SYNTAX      INTEGER
    ACCESS      read-only
    STATUS      mandatory
    DESCRIPTION "The number of times the local side (this unit) has
                 initiated a modem carrier retrain."
    ::= { diactEntry 61 }

  diactRemoteRenegotiates OBJECT-TYPE
    SYNTAX      INTEGER
    ACCESS      read-only
    STATUS      mandatory
    DESCRIPTION "The number of times the far modem has
                 initiated a modem speed renogotiate."
    ::= { diactEntry 62 }

  diactRemoteRetrains OBJECT-TYPE
    SYNTAX      INTEGER
    ACCESS      read-only
    STATUS      mandatory
    DESCRIPTION "The number of times the far modem has
                 initiated a modem carrier retrain."
    ::= { diactEntry 63 }

  diStatLcpRemoteMRRU OBJECT-TYPE
    SYNTAX      INTEGER
    ACCESS      read-only
    STATUS      mandatory
    DESCRIPTION "Multilink max. receive reconstruction unit
                 for the remote device."
    ::= { diactEntry 64 }

  diStatLcpLocalMRRU OBJECT-TYPE
    SYNTAX      INTEGER
    ACCESS      read-only
    STATUS      mandatory
    DESCRIPTION "Multilink max. receive reconstruction unit
                 for the local device."
    ::= { diactEntry 65 }

  diStatLcpAuth OBJECT-TYPE
    SYNTAX      LcpAuth
    ACCESS      read-only
    STATUS      mandatory
    DESCRIPTION "LCP authentication."
    ::= { diactEntry 66 }

  diactForceNextHop OBJECT-TYPE
    SYNTAX      IpAddress
    ACCESS      read-only
    STATUS      mandatory
    DESCRIPTION "If non zero, indicates the next hop that all packets
                 received on this dialup connection will be sent to.
                 The next hopp must be directly connected to the RAS.
                 This is activated using RADIUS attribute 209"
    ::= { diactEntry 67 }

  diStatIpFilterA OBJECT-TYPE SYNTAX OCTET STRING ACCESS read-only STATUS mandatory
    DESCRIPTION "Filter specification A ID" ::= { diactEntry 70 }
  diStatIpFilterB OBJECT-TYPE SYNTAX OCTET STRING ACCESS read-only STATUS mandatory
    DESCRIPTION "Filter specification B ID" ::= { diactEntry 71 }
  diStatIpFilterC OBJECT-TYPE SYNTAX OCTET STRING ACCESS read-only STATUS mandatory
    DESCRIPTION "Filter specification C ID" ::= { diactEntry 72 }
  diStatIpFilterD OBJECT-TYPE SYNTAX OCTET STRING ACCESS read-only STATUS mandatory
    DESCRIPTION "Filter specification D ID" ::= { diactEntry 73 }
  diStatIpFilterE OBJECT-TYPE SYNTAX OCTET STRING ACCESS read-only STATUS mandatory
    DESCRIPTION "Filter specification E ID" ::= { diactEntry 74 }
  diStatIpFilterF OBJECT-TYPE SYNTAX OCTET STRING ACCESS read-only STATUS mandatory
    DESCRIPTION "Filter specification F ID" ::= { diactEntry 75 }
  diStatIpFilterG OBJECT-TYPE SYNTAX OCTET STRING ACCESS read-only STATUS mandatory
    DESCRIPTION "Filter specification G ID" ::= { diactEntry 76 }
  diStatIpFilterH OBJECT-TYPE SYNTAX OCTET STRING ACCESS read-only STATUS mandatory
    DESCRIPTION "Filter specification H ID" ::= { diactEntry 77 }
  diStatIpFilterI OBJECT-TYPE SYNTAX OCTET STRING ACCESS read-only STATUS mandatory
    DESCRIPTION "Filter specification I ID" ::= { diactEntry 78 }
  diStatIpFilterJ OBJECT-TYPE SYNTAX OCTET STRING ACCESS read-only STATUS mandatory
    DESCRIPTION "Filter specification J ID" ::= { diactEntry 79 }


--**** Leave some space for more filters: diactEntry 80 - 99


  diactPrimaryDNS OBJECT-TYPE
    SYNTAX      IpAddress
    ACCESS      read-only
    STATUS      mandatory
    DESCRIPTION "This the DNS we got from Radius
                 This is activated using RADIUS attribute 135"
    ::= { diactEntry 100 }

  diactSecondaryDNS OBJECT-TYPE
    SYNTAX      IpAddress
    ACCESS      read-only
    STATUS      mandatory
    DESCRIPTION "This the DNS we got from Radius
                 This is activated using RADIUS attribute 136"
    ::= { diactEntry 101 }



  --*************************************************************************
  --*************************************************************************
  --                                 Dial Out
  --*************************************************************************
  --*************************************************************************

  doLoginTechnique OBJECT-TYPE
    SYNTAX      INTEGER {
                  none(1),
                  text(2)
                }
    ACCESS      read-write
    STATUS      mandatory
    DESCRIPTION "This variable defines the login sequence that a dial-up
                user will see.  The options are defined below:

                None
                Simply connection to the TCP pipe allows dialout.

                Text
                A Username prompt is displayed and a username must be entered.
                If the received username is a static user with no password
                defined then the connection completes and no password prompt.
                Otherwise a password prompt is displayed and a password must
                be entered."

    ::= { calldialout 1 }

  doUsernamePrompt OBJECT-TYPE
    SYNTAX      DisplayString (SIZE (0..39))
    ACCESS      read-write
    STATUS      mandatory
    DESCRIPTION "This defines the character string that will be displayed
                at user authentication time to request the users name.
                This should be a ASCII printable string and can include
                charrage returns and line feeds."
    ::= { calldialout 2 }

  doPasswordPrompt OBJECT-TYPE
    SYNTAX      DisplayString (SIZE (0..39))
    ACCESS      read-write
    STATUS      mandatory
    DESCRIPTION "This defines the character string that will be displayed
                at user authentication time to request the users password.
                This should be a ASCII printable string and can include
                charrage returns and line feeds."
    ::= { calldialout 3 }

  doBanner OBJECT-TYPE
    SYNTAX      DisplayString (SIZE (0..254))
    ACCESS      read-write
    STATUS      mandatory
    DESCRIPTION "A string to initially display for the user."
    ::= { calldialout 4 }

  doFailureBanner OBJECT-TYPE
    SYNTAX      DisplayString (SIZE (0..254))
    ACCESS      read-write
    STATUS      mandatory
    DESCRIPTION "This defines a message that will be displayed to a
                user when authentication failed.  This is only
                relevant when the authentication technique was Text."
    ::= { calldialout 5 }

  doAllowAttempts OBJECT-TYPE
    SYNTAX      INTEGER
    ACCESS      read-write
    STATUS      mandatory
    DESCRIPTION "The maximum number of attempts a user will be given to
                login before being disconnected.  This applies to Text
                authentications only.  PAP and CHAP authentications are
                only allowed a single attempt."
    ::= { calldialout 6 }

  doTcpPort OBJECT-TYPE
    SYNTAX      INTEGER
    ACCESS      read-write
    STATUS      mandatory
    DESCRIPTION "The TCP port number which the dialout should listen on
                 for connections."
    ::= { calldialout 7 }

  doRestrictToLan OBJECT-TYPE
    SYNTAX      INTEGER {
                  disable(1),
                  enable(2)
                }
    ACCESS      read-write
    STATUS      mandatory
    DESCRIPTION "Enabling the restriction to LAN will stop dialout attempts
                 which originate at any port besides the LAN port."

    ::= { calldialout 8 }

  doSessionTimeout OBJECT-TYPE
    SYNTAX      INTEGER
    ACCESS      read-write
    STATUS      mandatory
    DESCRIPTION "This is the maximum time in minutes which a connection
                is allowed to be maintained.  After this time the connection
                will be terminated, even if there is acive traffic on the
                connection.

                This is a default setting which may be overridden by
                the authentication of a specific user."
    ::= { calldialout 9 }

  doIdleTimeout OBJECT-TYPE
    SYNTAX      INTEGER
    ACCESS      read-write
    STATUS      mandatory
    DESCRIPTION "This is the maximum time in minutes which a connection
                is allowed to be maintained with no traffic.  After this
                time, if no traffic is seen, the connection will be
                terminated.

                This is a default setting which may be overridden by
                the authentication of a specific user."
    ::= { calldialout 10 }

  doLoginTimeout OBJECT-TYPE
    SYNTAX      INTEGER
    ACCESS      read-write
    STATUS      mandatory
    DESCRIPTION "This is the maximum time in seconds which a user is given
                to login.  This is only relevant before the user is
                authenticated.  This setting should take into account any
                time required to querry a remote authentication server
                (ie. RADIUS)."
    ::= { calldialout 11 }

  doLingerTime OBJECT-TYPE
    SYNTAX      INTEGER
    ACCESS      read-write
    STATUS      mandatory
    DESCRIPTION "Number of seconds a MIB entry in the Active
                 table will remain after the call is dead."
    ::= { calldialout 12 }

  doActive OBJECT-TYPE
    SYNTAX      INTEGER
    ACCESS      read-write
    STATUS      mandatory
    DESCRIPTION "The total number of active calls."
    ::= { calldialout 13 }


  doModemISDNEnable OBJECT-TYPE
    SYNTAX      INTEGER {
      disable(0),
      enable(1)
      }
    ACCESS      read-write
    STATUS      mandatory
    DESCRIPTION "Allow V34 and V34 annex 12 modulations"
    ::= { calldialout 14 }

  doModemV92Enable OBJECT-TYPE
    SYNTAX      INTEGER {
      disable(0),
      enable(1)
      }
    ACCESS      read-write
    STATUS      mandatory
    DESCRIPTION "Allow V92 modulations"
    ::= { calldialout 29 }

  doModemV90Enable OBJECT-TYPE
    SYNTAX      INTEGER {
      disable(0),
      enable(1)
      }
    ACCESS      read-write
    STATUS      mandatory
    DESCRIPTION "Allow V34 and V34 annex 12 modulations"
    ::= { calldialout 30 }

  doModemK56Enable OBJECT-TYPE
    SYNTAX      INTEGER {
      disable(0),
      enable(1)
      }
    ACCESS      read-write
    STATUS      mandatory
    DESCRIPTION "Allow V34 and V34 annex 12 modulations"
    ::= { calldialout 31 }

  doModemV34Enable OBJECT-TYPE
    SYNTAX      INTEGER {
      disable(0),
      enable(1)
      }
    ACCESS      read-write
    STATUS      mandatory
    DESCRIPTION "Allow V34 and V34 annex 12 modulations"
    ::= { calldialout 15 }

  doModemV32Enable OBJECT-TYPE
    SYNTAX  INTEGER {
      disable(0),
      enable(1)
      }
    ACCESS      read-write
    STATUS      mandatory
    DESCRIPTION "Allow V32 and V32bis modulations"
    ::= { calldialout 16 }

  doModemV23Enable OBJECT-TYPE
    SYNTAX      INTEGER {
      disable(0),
      enable(1)
      }
    ACCESS      read-write
    STATUS      mandatory
    DESCRIPTION "Allow V34 and V34 annex 12 modulations"
    ::= { calldialout 32 }

  doModemV22Enable OBJECT-TYPE
    SYNTAX      INTEGER {
      disable(0),
      enableV22(1),
      enableBell212(2)
      }
    ACCESS      read-write
    STATUS      mandatory
    DESCRIPTION "Allow V22 or Bell 212 modulations"
    ::= { calldialout 17 }

  doModemV21Enable OBJECT-TYPE
    SYNTAX      INTEGER {
      disable(0),
      enableV21(1),
      enableBell103(2)
      }
    ACCESS      read-write
    STATUS      mandatory
    DESCRIPTION "Allow V21 or Bell 103 modulations"
    ::= { calldialout 18 }

  doModemMaxSpeed OBJECT-TYPE
    SYNTAX      INTEGER
    ACCESS      read-write
    STATUS      mandatory
    DESCRIPTION "This variable allows the selection of the fastest
                 data rate that will be negotiated."
    ::= { calldialout 19 }

  doModemMinSpeed OBJECT-TYPE
    SYNTAX      INTEGER
    ACCESS      read-write
    STATUS      mandatory
    DESCRIPTION "This variable allows the selection of the slowest
                 data rate that will be negotiated."
    ::= { calldialout 20 }

  doModemGuardTone OBJECT-TYPE
    SYNTAX  INTEGER {
      toneNone(1),
      tone1800(3)
      }
    ACCESS      read-write
    STATUS      mandatory
    DESCRIPTION "Normally a guard tone is not required.  But, one can be
                 inserted.  This operates for Phase Shift Key modulations only."
    ::= { calldialout 21 }

  doModemCarrierLossDuration OBJECT-TYPE
    SYNTAX      INTEGER (1..255)
    ACCESS      read-write
    STATUS      mandatory
    DESCRIPTION "The number of seconds the carrier must be 
                 lost before it is considered the connection dead. A
                 setting above 100 indicates forever."
    ::= { calldialout 22 }

  doModemRetrain OBJECT-TYPE
    SYNTAX      INTEGER {
      none(0),
      retrain(1),
      fallForwardFallBack(2)
      }
    ACCESS      read-write
    STATUS      mandatory
    DESCRIPTION "Allow the modem to monitor the line quality and 
                 request a fallback or retrain for poor quality and a
                 fallforward for good quality."
    ::= { calldialout 23 }

  doModemTxLevel OBJECT-TYPE
    SYNTAX      INTEGER (0..15)
    ACCESS      read-write
    STATUS      mandatory
    DESCRIPTION "This variable should be set with caution; and normally
                 only after talking to a factory representative.  This
                 sets the transmit level power level of the modem.  The
                 scale is 0 (0 dB) to 15 (-15 dB).   Note that larger
                 numbers mean less power."
    ::= { calldialout 24 }

  doModemProtocol OBJECT-TYPE
    SYNTAX      INTEGER {
      direct(0),
      requestV42(1),
      requireV42(2)
      }
    ACCESS      read-write
    STATUS      mandatory
    DESCRIPTION "Selection of the data protocol to use on the modem.
                 This allows the request of or forcing of V42
                 error correction protocol."
    ::= { calldialout 25 }

  doModemCompression OBJECT-TYPE
    SYNTAX      INTEGER {
      direct(0),
      requestV42bis(1),
      requireV42bis(2),
      v44(3)
      }
    ACCESS      read-write
    STATUS      mandatory
    DESCRIPTION "Selection of the data compression protocol to use on 
                 the modem. This allows the request of or forcing of 
                 V42 compression protocol.  This will only be 
                 used if V42 error correction is active."
    ::= { calldialout 26 }

  doModemRestrictMods OBJECT-TYPE
    SYNTAX      INTEGER {
      disable(0),
      enable(1)
      }
    ACCESS      read-write
    STATUS      mandatory
    DESCRIPTION "Enabling this feature will restrict the dialout user
                 from modifying the modem settings.  Normally the 
                 dialout user has the abillity to alter the desired
                 modem operation through the use of AT commands."
    ::= { calldialout 27 }

  doServiceType OBJECT-TYPE
    SYNTAX      INTEGER {
      telnet(0),
      tcpClear(1)
      }
    ACCESS      read-write
    STATUS      mandatory
    DESCRIPTION "Selection of the TCp service type which will be
                 placed on the TCP connection when established."
    ::= { calldialout 28 }

-- V.92 settings

  doV92QuickConnect OBJECT-TYPE
    SYNTAX      INTEGER {
      disable(0),
      enable(1)
      }
    ACCESS      read-write
    STATUS      mandatory
    DESCRIPTION "Allow V92 Quick Connect"
    ::= { calldialout 33 }

  doV92ModemOnHold OBJECT-TYPE
    SYNTAX      INTEGER {
      disable(0),
      enable(1)
      }
    ACCESS      read-write
    STATUS      mandatory
    DESCRIPTION "Allow V92 Modem on Hold"
    ::= { calldialout 34 }

  doV92ModemOnHoldTimeout OBJECT-TYPE
    SYNTAX      INTEGER {
      disabled(0),
      ten-sec(1),
      twenty-sec(2),
      thirty-sec(3),
      forty-sec(4),
      one-min(5),
      two-min(6),
      three-min(7),
      four-min(8),
      six-min(9),
      eight-min(10),
      twelve-min(11),
      sixteen-min(12),
      never(13)
      }
    ACCESS      read-write
    STATUS      mandatory
    DESCRIPTION "v.92 modem on hold timeout period"
    ::= { calldialout 35 }

  doPageSort OBJECT-TYPE
    SYNTAX      INTEGER{
                descending(0),
                ascending(1)
                }			
    ACCESS      read-write
    STATUS      mandatory
    DESCRIPTION "sorts calls on dial-out page
				 0 - most recent calls at bottom
				 1 - most recent calls at top"
    ::= { calldialout 36 }

  doTotalCallAttempts OBJECT-TYPE
    SYNTAX      INTEGER
    ACCESS      read-write
    STATUS      mandatory
    DESCRIPTION "The total number of calls which have been attempted since
                 the last boot of the box."
    ::= { calldialout 37 }

  doMaxActive OBJECT-TYPE
    SYNTAX      INTEGER
    ACCESS      read-write
    STATUS      mandatory
    DESCRIPTION "The maximum number of active calls seen at one time."
    ::= { calldialout 38 }

  --*************************************************************************
  -- Table of individual active calls

  doactTable OBJECT-TYPE
    SYNTAX      SEQUENCE OF DoactEntry
    ACCESS      not-accessible
    STATUS      mandatory
    DESCRIPTION "Table of individual active calls."
    ::= { calldialout 100 }

  doactEntry OBJECT-TYPE
    SYNTAX       DoactEntry
    ACCESS       not-accessible
    STATUS       mandatory
    DESCRIPTION  "An entry of an active call."
    INDEX        { doactIndex }
    ::= { doactTable 1 }

  DoactEntry ::=
    SEQUENCE {
      doactIndex                  Index,
      doactState                  INTEGER,
      doactDSPIndex               INTEGER,
      doactLinkIndex              INTEGER,
      doactSlotIndex              INTEGER,
      doactSessionTime            TimeTicks,
      doactRemainingIdle          INTEGER,
      doactRemainingSession       TimeTicks,
      doactNumberDialed           DisplayString,
      doactSentOctets             Counter,
      doactReceivedOctets         Counter,
      doactSentDataFrames         INTEGER,
      doactReceivedDataFrames     INTEGER,
      doactErrorFrames            INTEGER,
      doactModulation             INTEGER,
      doactErrorCorrection        INTEGER,
      doactCompression            INTEGER,
      doactSymbolRate             INTEGER,
      doactUsername               DisplayString,
      doactPassword               DisplayString,
      doactTerminateReason        TerminateReason,
      doactLocalRenegotiates      INTEGER,
      doactLocalRetrains          INTEGER,
      doactRemoteRenegotiates     INTEGER,
      doactRemoteRetrains         INTEGER,
      doactTxSpeed                INTEGER,
      doactRxSpeed                INTEGER,
      doactIP                     IpAddress,
      doactMultiLinkFlag          INTEGER,
      doactMultiIndex             INTEGER,
      doactSessionStartTime       TimeTicks,
      doStatBadAddresses          INTEGER,
      doStatBadControls           Counter,
      doStatPacketTooLongs        Counter,
      doStatBadFCSs               Counter,
      doStatLocalMRU              INTEGER,
      doStatRemoteMRU             INTEGER,
      doStatLocalToPeerACCMap     OCTET STRING,
      doStatPeerToLocalACCMap     OCTET STRING,
      doStatLocalToRemoteProtComp EnabledDisabled,
      doStatRemoteToLocalProtComp EnabledDisabled,
      doStatLocalToRemoteACComp   EnabledDisabled,
      doStatRemoteToLocalACComp   EnabledDisabled,
      doStatTransmitFcsSize       FcsSize,
      doStatReceiveFcsSize        FcsSize,
      doStatLcpRemoteMRRU         INTEGER,
      doStatLcpLocalMRRU          INTEGER,
      doStatLcpAuth               LcpAuth
    }

  doactIndex OBJECT-TYPE
    SYNTAX      Index
    ACCESS      read-only
    STATUS      mandatory
    DESCRIPTION "Unique identification of this active call
                 (use linkTAble.linkTimeSlot.activeIndex)."
    ::= { doactEntry 1 }

  doactState OBJECT-TYPE
    SYNTAX      INTEGER {
                  unknown(0),
                  commandmode(1),
                  ringing(2),
                  connecting(3),
                  lcpNegotiate(4),
                  authenticating(5),
                  tcpEstablish(6),
                  online(7),
                  disconnecting(8),
                  cleaningup(9),
                  dead(10),
                  kill(11),
                  bury(12),
                  l2tpTunneled(13),
                  waitingForIpcp(14),
                  waitingRedial(15),
                  waitingOnDemand(16)
                  }
    ACCESS      read-write
    STATUS      mandatory
    DESCRIPTION "Indicates current progress"
    ::= { doactEntry 2 }

  doactDSPIndex OBJECT-TYPE
    SYNTAX      INTEGER
    ACCESS      read-only
    STATUS      mandatory
    DESCRIPTION "Which DSP chip this call is on
                 (points to DSP table)."
    ::= { doactEntry 3 }

  doactLinkIndex OBJECT-TYPE
    SYNTAX      INTEGER
    ACCESS      read-only
    STATUS      mandatory
    DESCRIPTION "Which WAN link this call is on
                 (points to the Link table)."
    ::= { doactEntry 4 }

  doactSlotIndex OBJECT-TYPE
    SYNTAX      INTEGER
    ACCESS      read-only
    STATUS      mandatory
    DESCRIPTION "Which time slot this call is on
                 (points to the Fractional table)."
    ::= { doactEntry 5 }

  doactSessionTime OBJECT-TYPE
    SYNTAX      TimeTicks
    ACCESS      read-only
    STATUS      mandatory
    DESCRIPTION "The number of seconds this call was/is active."
    ::= { doactEntry 6 }

  doactRemainingIdle OBJECT-TYPE
    SYNTAX      INTEGER
    ACCESS      read-only
    STATUS      mandatory
    DESCRIPTION "Number of minutes until idle timeout (counts down)."
    ::= { doactEntry 7 }

  doactRemainingSession OBJECT-TYPE
    SYNTAX      TimeTicks
    ACCESS      read-only
    STATUS      mandatory
    DESCRIPTION "Number of seconds left in this session (counts down)."
    ::= { doactEntry 8 }

  doactNumberDialed OBJECT-TYPE
    SYNTAX      DisplayString
    ACCESS      read-only
    STATUS      mandatory
    DESCRIPTION "The phone number that was dialed into."
    ::= { doactEntry 9 }

  doactSentOctets OBJECT-TYPE
    SYNTAX      Counter
    ACCESS      read-only
    STATUS      mandatory
    DESCRIPTION "The number of octets sent on this call."
    ::= { doactEntry 10 }

  doactReceivedOctets OBJECT-TYPE
    SYNTAX      Counter
    ACCESS      read-only
    STATUS      mandatory
    DESCRIPTION "The number of octets received on this call."
    ::= { doactEntry 11 }

  doactSentDataFrames OBJECT-TYPE
    SYNTAX      INTEGER
    ACCESS      read-only
    STATUS      mandatory
    DESCRIPTION "The number of sent packets on this call."
    ::= { doactEntry 12 }

  doactReceivedDataFrames OBJECT-TYPE
    SYNTAX      INTEGER
    ACCESS      read-only
    STATUS      mandatory
    DESCRIPTION "The number of received packets on this call."
    ::= { doactEntry 13 }

  doactErrorFrames OBJECT-TYPE
    SYNTAX      INTEGER
    ACCESS      read-only
    STATUS      mandatory
    DESCRIPTION "Number of bad received packets (CRC, Length,...)."
    ::= { doactEntry 14 }

  doactModulation OBJECT-TYPE
    SYNTAX      ModemModulation
    ACCESS      read-only
    STATUS      mandatory
    DESCRIPTION "The modulation of the link."
    ::= { doactEntry 15 }

  doactErrorCorrection OBJECT-TYPE
    SYNTAX      INTEGER {
                  unknown(0),
                  none(1),
                  v42(2),
                  mnp(3),
                  v120(4),
                  cellular(5),
                  hdlc(6)
                }
    ACCESS      read-only
    STATUS      mandatory
    DESCRIPTION "The error correction scheme used on this call."
    ::= { doactEntry 16 }

  doactCompression OBJECT-TYPE
    SYNTAX      INTEGER {
                  unknown(0),
                  none(1),
                  v42bis(2),
                  mnp5(3),
                  stac(4),
                  v44(5)
                }
    ACCESS      read-only
    STATUS      mandatory
    DESCRIPTION "The compression technique used on this call."
    ::= { doactEntry 17 }

  doactSymbolRate OBJECT-TYPE
    SYNTAX      INTEGER
    ACCESS      read-only
    STATUS      mandatory
    DESCRIPTION "The symbol rate of the call (modem only)."
    ::= { doactEntry 18 }

  doactUsername OBJECT-TYPE
    SYNTAX      DisplayString
    ACCESS      read-only
    STATUS      mandatory
    DESCRIPTION "The username that the caller entered."
    ::= { doactEntry 19 }

  doactPassword OBJECT-TYPE
    SYNTAX      DisplayString
    ACCESS      read-only
    STATUS      mandatory
    DESCRIPTION "The password that the caller entered."
    ::= { doactEntry 20 }

  doactTerminateReason OBJECT-TYPE
    SYNTAX      TerminateReason
    ACCESS      read-only
    STATUS      mandatory
    DESCRIPTION "The reason a call was disconnected."
    ::= { doactEntry 21 }

  doactLocalRenegotiates OBJECT-TYPE
    SYNTAX      INTEGER
    ACCESS      read-only
    STATUS      mandatory
    DESCRIPTION "The number of times the local side (this unit) has
                 initiated a modem speed renogotiate."
    ::= { doactEntry 22 }

  doactLocalRetrains OBJECT-TYPE
    SYNTAX      INTEGER
    ACCESS      read-only
    STATUS      mandatory
    DESCRIPTION "The number of times the local side (this unit) has
                 initiated a modem carrier retrain."
    ::= { doactEntry 23 }

  doactRemoteRenegotiates OBJECT-TYPE
    SYNTAX      INTEGER
    ACCESS      read-only
    STATUS      mandatory
    DESCRIPTION "The number of times the far modem has
                 initiated a modem speed renogotiate."
    ::= { doactEntry 24 }

  doactRemoteRetrains OBJECT-TYPE
    SYNTAX      INTEGER
    ACCESS      read-only
    STATUS      mandatory
    DESCRIPTION "The number of times the far modem has
                 initiated a modem carrier retrain."
    ::= { doactEntry 25 }

  doactTxSpeed OBJECT-TYPE
    SYNTAX      INTEGER
    ACCESS      read-only
    STATUS      mandatory
    DESCRIPTION "The connected transmit-speed of the link."
    ::= { doactEntry 26 }

  doactRxSpeed OBJECT-TYPE
    SYNTAX      INTEGER
    ACCESS      read-only
    STATUS      mandatory
    DESCRIPTION "The connected receive-speed of the link."
    ::= { doactEntry 27 }

  doactIP OBJECT-TYPE
    SYNTAX      IpAddress
    ACCESS      read-only
    STATUS      mandatory
    DESCRIPTION "The current IP address."
    ::= { doactEntry 28 }

  doactMultiLinkFlag OBJECT-TYPE
    SYNTAX      INTEGER (0..1)
    ACCESS      read-only
    STATUS      mandatory
    DESCRIPTION "An indicator of whether this is a multilink
                 call or not.  0 is FALSE, 1 is TRUE."
    ::= { doactEntry 29 }

  doactMultiIndex OBJECT-TYPE
    SYNTAX      INTEGER
    ACCESS      read-only
    STATUS      mandatory
    DESCRIPTION "Unique identification shared between
                 multilink active calls."
    ::= { doactEntry 30 }

  doactSessionStartTime OBJECT-TYPE
    SYNTAX      TimeTicks
    ACCESS      read-only
    STATUS      mandatory
    DESCRIPTION "The number of seconds this call was/is active."
    ::= { doactEntry 31 }

  doStatBadAddresses OBJECT-TYPE
    SYNTAX      INTEGER
    ACCESS      read-only
    STATUS      mandatory
    DESCRIPTION "Statistics on the link."
    ::= { doactEntry 32 }

  doStatBadControls OBJECT-TYPE
    SYNTAX      Counter
    ACCESS      read-only
    STATUS      mandatory
    DESCRIPTION "The number of packets received on this call
                 with an incorrect Control Field."
    ::= { doactEntry 33 }

  doStatPacketTooLongs OBJECT-TYPE
    SYNTAX      Counter
    ACCESS      read-only
    STATUS      mandatory
    DESCRIPTION "The number of received packets that have been
                 discarded because their length exceeded the
                 MRU."
    ::= { doactEntry 34 }

  doStatBadFCSs OBJECT-TYPE
    SYNTAX      Counter
    ACCESS      read-only
    STATUS      mandatory
    DESCRIPTION "The number of received packets that have been
                 discarded due to having an incorrect FCS."
    ::= { doactEntry 35 }

  doStatLocalMRU OBJECT-TYPE
    SYNTAX      INTEGER
    ACCESS      read-only
    STATUS      mandatory
    DESCRIPTION "The current value of the local Maximum Transfer
                 Unit (MRU) for PPP and SLIP."
    ::= { doactEntry 36 }

  doStatRemoteMRU OBJECT-TYPE
    SYNTAX      INTEGER
    ACCESS      read-only
    STATUS      mandatory
    DESCRIPTION "The current value of the remote Maximum Transfer
                 Unit (MRU) for PPP and SLIP."
    ::= { doactEntry 37 }

  doStatLocalToPeerACCMap OBJECT-TYPE
    SYNTAX      OCTET STRING
    ACCESS      read-only
    STATUS      mandatory
    DESCRIPTION "The current value of the ACC Map used for
                 sending packets from the local entity to
                 the remote entity."
    ::= { doactEntry 38 }

  doStatPeerToLocalACCMap OBJECT-TYPE
    SYNTAX      OCTET STRING
    ACCESS      read-only
    STATUS      mandatory
    DESCRIPTION "The current value of the ACC Map used for
                 sending packets from the remote entity to
                 the local entity."
    ::= { doactEntry 39 }

  doStatLocalToRemoteProtComp OBJECT-TYPE
    SYNTAX      EnabledDisabled
    ACCESS      read-only
    STATUS      mandatory
    DESCRIPTION "Indicates whether the local entity will
                 use Protocol Compression when transmitting
                 packets to the remote entity."
    ::= { doactEntry 40 }

  doStatRemoteToLocalProtComp OBJECT-TYPE
    SYNTAX      EnabledDisabled
    ACCESS      read-only
    STATUS      mandatory
    DESCRIPTION "Indicates whether the local entity will
                 use Protocol Compression when transmitting
                 packets to the remote entity."
    ::= { doactEntry 41 }

  doStatLocalToRemoteACComp OBJECT-TYPE
    SYNTAX      EnabledDisabled
    ACCESS      read-only
    STATUS      mandatory
    DESCRIPTION "Indicates whether the local entity will
                 use Address and Control Compression when
                 transmitting packets to the remote entity."
    ::= { doactEntry 42 }

  doStatRemoteToLocalACComp OBJECT-TYPE
    SYNTAX      EnabledDisabled
    ACCESS      read-only
    STATUS      mandatory
    DESCRIPTION "Indicates whether the remote entity will
                 use Address and Control Compression when
                 transmitting packets to the local entity."
    ::= { doactEntry 43 }

  doStatTransmitFcsSize OBJECT-TYPE
    SYNTAX      FcsSize
    ACCESS      read-only
    STATUS      mandatory
    DESCRIPTION "The size of the Frame Check Sequence (FCS) in
                 bits that the local node will generate when
                 sending packets to the remote node."
    ::= { doactEntry 44 }

  doStatReceiveFcsSize OBJECT-TYPE
    SYNTAX      FcsSize
    ACCESS      read-only
    STATUS      mandatory
    DESCRIPTION "The size of the Frame Check Sequence (FCS) in
                 bits that the local node will generate when
                 sending packets to the remote node."
    ::= { doactEntry 45 }

  doStatLcpRemoteMRRU OBJECT-TYPE
    SYNTAX      INTEGER
    ACCESS      read-only
    STATUS      mandatory
    DESCRIPTION "Multilink max. receive reconstruction unit
                 for the remote device."
    ::= { doactEntry 46 }

  doStatLcpLocalMRRU OBJECT-TYPE
    SYNTAX      INTEGER
    ACCESS      read-only
    STATUS      mandatory
    DESCRIPTION "Multilink max. receive reconstruction unit
                 for the local device."
    ::= { doactEntry 47 }

  doStatLcpAuth OBJECT-TYPE
    SYNTAX      LcpAuth
    ACCESS      read-only
    STATUS      mandatory
    DESCRIPTION "LCP authentication."
    ::= { doactEntry 48 }

  --*************************************************************************
  --*************************************************************************
  --                           Drop and Insert
  --*************************************************************************
  --*************************************************************************

  drSessionTimeout OBJECT-TYPE
    SYNTAX      INTEGER
    ACCESS      read-write
    STATUS      mandatory
    DESCRIPTION "This is the maximum time in minutes which a connection
                is allowed to be maintained.  After this time the connection
                will be terminated, even if there is acive traffic on the
                connection."
    ::= { dropinsert 1 }

  drLingerTime OBJECT-TYPE
    SYNTAX      INTEGER
    ACCESS      read-write
    STATUS      mandatory
    DESCRIPTION "Number of seconds a MIB entry in the Active
                 table will remain after the call is dead."
    ::= { dropinsert 2 }

  drActive OBJECT-TYPE
    SYNTAX      INTEGER
    ACCESS      read-write
    STATUS      mandatory
    DESCRIPTION "The total number of active calls."
    ::= { dropinsert 3 }

  --*************************************************************************
  -- Table of individual active calls

  dractTable OBJECT-TYPE
    SYNTAX      SEQUENCE OF DractEntry
    ACCESS      not-accessible
    STATUS      mandatory
    DESCRIPTION "Table of individual active calls."
    ::= { dropinsert 100 }

  dractEntry OBJECT-TYPE
    SYNTAX       DractEntry
    ACCESS       not-accessible
    STATUS       mandatory
    DESCRIPTION  "An entry of an active call."
    INDEX        { dractIndex }
    ::= { dractTable 1 }

  DractEntry ::=
    SEQUENCE {
      dractIndex                  Index,
      dractState                  INTEGER,
      dractLinkIndex              INTEGER,
      dractChannel                INTEGER,
      dractPassLinkIndex          INTEGER,
      dractPassChannel            INTEGER,
      dractSessionTime            TimeTicks,
      dractRemainingSession       TimeTicks,
      dractNumberDialed           DisplayString,
      dractCallingPhone           DisplayString
    }

  dractIndex OBJECT-TYPE
    SYNTAX      Index
    ACCESS      read-only
    STATUS      mandatory
    DESCRIPTION "Unique identification of this active call"
    ::= { dractEntry 1 }

  dractState OBJECT-TYPE
    SYNTAX      INTEGER {
                  setup(1),
                  alerting(2),
                  flash(3),
                  online(4),
                  sessiontime(5),
                  clearForward(6),
                  clearBackward(7),
                  dead(8),
                  kill(9)
                }
    ACCESS      read-write
    STATUS      mandatory
    DESCRIPTION "Indicates current progress"
    ::= { dractEntry 2}

  dractLinkIndex OBJECT-TYPE
    SYNTAX      INTEGER
    ACCESS      read-only
    STATUS      mandatory
    DESCRIPTION "Which WAN link this call originated on"
    ::= { dractEntry 3}

  dractChannel OBJECT-TYPE
    SYNTAX      INTEGER
    ACCESS      read-only
    STATUS      mandatory
    DESCRIPTION "Which channel this call originated on"
    ::= { dractEntry 4}

  dractPassLinkIndex OBJECT-TYPE
    SYNTAX      INTEGER
    ACCESS      read-only
    STATUS      mandatory
    DESCRIPTION "Which link this call was passed to"
    ::= { dractEntry 5}

  dractPassChannel OBJECT-TYPE
    SYNTAX      INTEGER
    ACCESS      read-only
    STATUS      mandatory
    DESCRIPTION "Which channel this call was passed to"
    ::= { dractEntry 6}

  dractSessionTime OBJECT-TYPE
    SYNTAX      TimeTicks
    ACCESS      read-only
    STATUS      mandatory
    DESCRIPTION "The number of seconds this call was/is active."
    ::= { dractEntry 7 }

  dractRemainingSession OBJECT-TYPE
    SYNTAX      TimeTicks
    ACCESS      read-only
    STATUS      mandatory
    DESCRIPTION "Number of seconds left in this session (counts down)."
    ::= { dractEntry 8 }

  dractNumberDialed OBJECT-TYPE
    SYNTAX      DisplayString
    ACCESS      read-only
    STATUS      mandatory
    DESCRIPTION "The phone number that was dialed into."
    ::= { dractEntry 9 }

  dractCallingPhone OBJECT-TYPE
    SYNTAX      DisplayString
    ACCESS      read-only
    STATUS      mandatory
    DESCRIPTION "The phone number that was dialed from."
    ::= { dractEntry 10 }

  --*************************************************************************
  --*************************************************************************
  --                         Authentication
  --*************************************************************************
  --*************************************************************************

  auValidation OBJECT-TYPE
    SYNTAX  INTEGER {
      noValidation(0),
      staticUsers(1),
      radiusUsers(2),
      tacacsUsers(3),
      staticThenRadius(4),
      staticThenTacacs(5)
      }
    ACCESS      read-write
    STATUS      mandatory
    DESCRIPTION "Incoming users must be validated.  This is true for dialup
                users as well as box maintenance.  The scheme chossen here
                will determine how a username and password are validated."
    ::= { authenticate 1 }

  auHostAddress OBJECT-TYPE
    SYNTAX      IpAddress
    ACCESS      read-write
    STATUS      mandatory
    DESCRIPTION "When using a remote authentication server (RADIUS or TACACS)
                this variable provides the IP address of the server."
    ::= { authenticate 3 }

  auSecondaryHostAddress OBJECT-TYPE
    SYNTAX      IpAddress
    ACCESS      read-write
    STATUS      mandatory
    DESCRIPTION "When using a remote authentication server (RADIUS or TACACS)
                this variable provides an alternative server IP address."
    ::= { authenticate 4 }

  auHostPort OBJECT-TYPE
    SYNTAX      INTEGER
    ACCESS      read-write
    STATUS      mandatory
    DESCRIPTION "When using a remote authentication server (RADIUS or TACACS)
                this variable provides the UDP port number of the server."
    ::= { authenticate 5 }

  auTimeout OBJECT-TYPE
    SYNTAX      INTEGER
    ACCESS      read-write
    STATUS      mandatory
    DESCRIPTION "When using a remote authentication server (RADIUS or TACACS)
                this variable provides the timeout in seconds before the box
                will retransmit the authentication request."
    ::= { authenticate 6 }

  auRetries OBJECT-TYPE
    SYNTAX      INTEGER
    ACCESS      read-write
    STATUS      mandatory
    DESCRIPTION "When using a remote authentication server (RADIUS or TACACS)
                this variable specifies the number of times the box will
                resend the authentication request.  Authentication requests
                are resent after a timeout."
    ::= { authenticate 7 }

  auSecret OBJECT-TYPE
    SYNTAX      OCTET STRING (SIZE (0..80))
    ACCESS      read-write
    STATUS      mandatory
    DESCRIPTION "When using a remote authentication server (RADIUS or TACACS)
                this variable specifies the shared secret which is used to
                encrypt the authentication request and reply."
    ::= { authenticate 8 }

  auNASIdentifier OBJECT-TYPE
    SYNTAX      OCTET STRING (SIZE (0..80))
    ACCESS      read-write
    STATUS      mandatory
    DESCRIPTION "When using a remote authentication server (RADIUS or TACACS)
                this variable is used to identify the box to the server.  If
                this field is null then the IP address of the box will be used."
    ::= { authenticate 9 }

  auAcctAddress OBJECT-TYPE
    SYNTAX      IpAddress
    ACCESS      read-write
    STATUS      mandatory
    DESCRIPTION "When using a remote accouting server (such as RADIUS
                Accounting) this variable provides the IP address of the
                accounting server."
    ::= { authenticate 13 }

  auSecondaryAcctAddress OBJECT-TYPE
    SYNTAX      IpAddress
    ACCESS      read-write
    STATUS      mandatory
    DESCRIPTION "When using a remote accouting server (such as RADIUS
                Accounting) this variable provides the IP address of the
                accounting server."
    ::= { authenticate 14 }

  auAcctPort OBJECT-TYPE
    SYNTAX      INTEGER
    ACCESS      read-write
    STATUS      mandatory
    DESCRIPTION "When using a remote accouting server (such as RADIUS
                Accounting) this variable provides the UDP port number of the
                accounting server."
    ::= { authenticate 15 }

  auAccoutingEnable OBJECT-TYPE
    SYNTAX  INTEGER {
      disableAccounting(0),
      enableAccounting(1),
      enableAccountingNoValidation(2)
      }
    ACCESS      read-write
    STATUS      mandatory
    DESCRIPTION "If Accounting is enabled then the type of accounting done
                depends on the validation technique being used.  Currently,
                only RADIUS accounting is supported."
    ::= { authenticate 16 }


  auRadiusPacketFormat OBJECT-TYPE
    SYNTAX  INTEGER {
      fullRfcPacket(0),
      minimumRfcPacket(1)
      }
    ACCESS      read-write
    STATUS      mandatory
    DESCRIPTION "When RADIUS packets are sent this object can adjust the
                 content of the packet.  These settings modify which
                 attributes are placed into the packet."
    ::= { authenticate 28 }

  auRadiusRunningIdSize OBJECT-TYPE
    SYNTAX      INTEGER {
                 eight(8),
                 twelve(12)
                }
    ACCESS      read-write
    STATUS      mandatory
    DESCRIPTION "When RADIUS accounting packets are sent, the session ID 
                 is included. This assists with creating a unique running
                 ID that is composed of the last 2 or 4 digits of the RAS
                 MAC address, and the number of times the box has reboot.
                 See RFC 2866 - page 15
                 sizeEight:   FF   F  FFFFF
                 sizeTwelve:  FFFF FF FFFFFF"
    ::= { authenticate 31 }

  auRadiusRunningId OBJECT-TYPE
    SYNTAX      DisplayString
    ACCESS      read-only
    STATUS      mandatory
    DESCRIPTION "This is the running ID mentioned previously to be sent to
                 the RADIUS server. It is composed of the lower four bytes
                 of the RAS MAC address and to bytes of the boot up count.
                 FFFF FF or FF F"
    ::= { authenticate 32 }


  --*************************************************************************
  -- Authentication Statistics

  auAuthenticationsValidTotal OBJECT-TYPE
    SYNTAX      INTEGER
    ACCESS      read-only
    STATUS      mandatory
    DESCRIPTION ""
    ::= { authenticate 17 }

  auAuthenticationsValidPrimary OBJECT-TYPE
    SYNTAX      INTEGER
    ACCESS      read-only
    STATUS      mandatory
    DESCRIPTION ""
    ::= { authenticate 18 }

  auAuthenticationsValidSecondary OBJECT-TYPE
    SYNTAX      INTEGER
    ACCESS      read-only
    STATUS      mandatory
    DESCRIPTION ""
    ::= { authenticate 19 }

  auAuthenticationsValidStatic OBJECT-TYPE
    SYNTAX      INTEGER
    ACCESS      read-only
    STATUS      mandatory
    DESCRIPTION ""
    ::= { authenticate 20 }

  auAuthenticationsDenied OBJECT-TYPE
    SYNTAX      INTEGER
    ACCESS      read-only
    STATUS      mandatory
    DESCRIPTION ""
    ::= { authenticate 21 }

  auPrimaryServerRetrys OBJECT-TYPE
    SYNTAX      INTEGER
    ACCESS      read-only
    STATUS      mandatory
    DESCRIPTION ""
    ::= { authenticate 22 }

  auSecondaryServerRetrys OBJECT-TYPE
    SYNTAX      INTEGER
    ACCESS      read-only
    STATUS      mandatory
    DESCRIPTION ""
    ::= { authenticate 23 }

  auAccountingServerRetrys OBJECT-TYPE
    SYNTAX      INTEGER
    ACCESS      read-only
    STATUS      mandatory
    DESCRIPTION ""
    ::= { authenticate 24 }

  auPrimaryServerTimeouts OBJECT-TYPE
    SYNTAX      INTEGER
    ACCESS      read-only
    STATUS      mandatory
    DESCRIPTION ""
    ::= { authenticate 25 }

  auSecondaryServerTimeouts OBJECT-TYPE
    SYNTAX      INTEGER
    ACCESS      read-only
    STATUS      mandatory
    DESCRIPTION ""
    ::= { authenticate 26 }

  auAccountingServerTimeouts OBJECT-TYPE
    SYNTAX      INTEGER
    ACCESS      read-only
    STATUS      mandatory
    DESCRIPTION ""
    ::= { authenticate 27 }

  auAuthenticationSlowestResponse OBJECT-TYPE
    SYNTAX      TimeTicks
    ACCESS      read-only
    STATUS      mandatory
    DESCRIPTION ""
    ::= { authenticate 29 }

  auAuthenticationLastResponse OBJECT-TYPE
    SYNTAX      TimeTicks
    ACCESS      read-only
    STATUS      mandatory
    DESCRIPTION ""
    ::= { authenticate 30 }

  --*************************************************************************
  -- Static user configuration table

  staticUsersTable OBJECT-TYPE
    SYNTAX      SEQUENCE OF StaticUsersEntry
    ACCESS      not-accessible
    STATUS      mandatory
    DESCRIPTION "Table of predefined static users."
    ::= { authenticate 40 }

  staticUsersEntry OBJECT-TYPE
    SYNTAX       StaticUsersEntry
    ACCESS       not-accessible
    STATUS       mandatory
    DESCRIPTION  "An entry in the table of predefined static users."
    INDEX        { suID }
    ::= { staticUsersTable 1 }

  StaticUsersEntry ::=
    SEQUENCE {
      suID              Index,
      suUsername        OCTET STRING,
      suPassword        OCTET STRING,
      suService         INTEGER,
      suServiceIP       IpAddress,
      suServicePort     INTEGER,
      suPortLimit       INTEGER,
      suServiceMask     IpAddress,
      suFilterId        INTEGER,
      suCallbackConfig  INTEGER,
      suCallbackNumber  DialedNumber
    }

  suID OBJECT-TYPE
    SYNTAX      Index
    ACCESS      read-write
    STATUS      mandatory
    DESCRIPTION "This object is the identifier of an entry in
                the list of statically defined users."
    ::= { staticUsersEntry 1 }

  suUsername OBJECT-TYPE
    SYNTAX      OCTET STRING (SIZE (1..19))
    ACCESS      read-write
    STATUS      mandatory
    DESCRIPTION "The predefined username exactly as it should be entered
                by a user.  This should be an ASCII printable string with
                no carrage returns or line feeds."
    ::= { staticUsersEntry 2 }

  suPassword OBJECT-TYPE
    SYNTAX      OCTET STRING (SIZE (0..19))
    ACCESS      read-write
    STATUS      mandatory
    DESCRIPTION "The predefined password exactly as it should be entered
                by a user.  This should be an ASCII printable string with
                no carrage returns or line feeds.  If a NULL password is
                configured then a password prompt will not be displayed
                to the user."
    ::= { staticUsersEntry 3 }

  suService OBJECT-TYPE
    SYNTAX  INTEGER {
      default(0),
      admin(1),
      monitor(2),
      rlogin(3),
      telnet(4),
      tcpraw(5),
      ppp(6),
      cppp(7),
      slip(8),
      cslip(9),
      dialout(10),
      vpn(11)
      }
    ACCESS      read-write
    STATUS      mandatory
    DESCRIPTION "Statically defined users must have a specific service
                type assigned to them.  A user will not be validated if
                the assigned service type does not match the connection
                which the users is attempting."
    ::= { staticUsersEntry 4 }

  suServiceIP OBJECT-TYPE
    SYNTAX      IpAddress
    ACCESS      read-write
    STATUS      mandatory
    DESCRIPTION "If the service type is a framed protocol then this
                will define the IP address of the user.  If the service
                type is a login connection (telnet,rlogin,vpn) then this
                will defined the IP address which the user is to be
                connected to.

                If the value is set to zero then the default IP address
                will be used as defined by the auServiceIP object or the
                IP address pool."
    ::= { staticUsersEntry 5 }

  suServicePort OBJECT-TYPE
    SYNTAX      INTEGER
    ACCESS      read-write
    STATUS      mandatory
    DESCRIPTION "This object is only relevant if the service type is a
                login connection (telnet,rlogin,vpn).  It will defined the
                TCP Port which the user is to be connected to.

                If the value is set to zero then the UNIX default port
                numbers will be used:
                    telnet   23
                    rlogin   513
                    l2tp     1701"
    ::= { staticUsersEntry 6 }

  suPortLimit OBJECT-TYPE
    SYNTAX      INTEGER
    ACCESS      read-write
    STATUS      mandatory
    DESCRIPTION "This object controls how many active sessions a single
                 static user can have.  0 = eternal"
    ::= { staticUsersEntry 7 }


  suServiceMask OBJECT-TYPE
    SYNTAX      IpAddress
    ACCESS      read-write
    STATUS      mandatory
    DESCRIPTION "If the service type is a framed protocol then this
                will define the IP mask of the user.  This will
                normally be set to 255.255.255.255 for a typical
                host connection.  But, in the case where the end user
                is a connection point to a complete subnet, this can
                be used to define the scope of the subnet.

                If the value is set to zero it will be forced to 
                the host mask of 255.255.255.255."
    ::= { staticUsersEntry 8 }

  suFilterId OBJECT-TYPE
    SYNTAX      INTEGER
    ACCESS      read-write
    STATUS      mandatory
    DESCRIPTION "A single filter can be specified with a static user.
                 It is identified here by its filter ID.  This number
                 is cross referenced to the filterip MIB."
    ::= { staticUsersEntry 9 }

  suCallbackConfig OBJECT-TYPE
    SYNTAX      INTEGER{
                noCallback(0),
                setByCaller(1),
                alwaysCallbackTo(2),
                callbackToCallingNum(3)
                }
    ACCESS      read-write
    STATUS      mandatory
    DESCRIPTION "Callback configuration for each user."
    ::= { staticUsersEntry 10 }

  suCallbackNumber OBJECT-TYPE
    SYNTAX      DialedNumber
    ACCESS      read-write
    STATUS      mandatory
    DESCRIPTION "Administrator defined callback number."
    ::= { staticUsersEntry 11 }

  --*************************************************************************
  --*************************************************************************
  --                         Testmanager
  --*************************************************************************
  --*************************************************************************

  testAction OBJECT-TYPE
    SYNTAX      INTEGER {
      disable(0),
      enable(1)
      }
    ACCESS      read-write
    STATUS      mandatory
    DESCRIPTION ""
    ::= { testmanager 1 }

  testFraming OBJECT-TYPE
    SYNTAX      INTEGER {
      noWan(0),
      t1d4(1),
      t1esf(2),
      e1(3),
      e1crc(4),
      e1mf(5),
      e1mfcrc(6),
      e1Transparent(7)
      }
    ACCESS      read-write
    STATUS      mandatory
    DESCRIPTION ""
    ::= { testmanager 2 }

  testPulse OBJECT-TYPE
    SYNTAX      INTEGER {
      triState(0),
      e1pulse(1),
      t1pulse0dB(2),
      t1pulse-7dB(3),
      t1pulse-15dB(4)
      }
    ACCESS      read-write
    STATUS      mandatory
    DESCRIPTION ""
    ::= { testmanager 3 }

  testPcm OBJECT-TYPE
    SYNTAX      INTEGER {
      ulawModem(0),
      alawModem(1),
      ulawDigitalMilliwatt(2),
      alawDigitalMilliwatt(3),
      pattern-2-15(4),
      lineLoopback(5),
      isdnHdlc(6),
      mfr2(7)
      }
    ACCESS      read-write
    STATUS      mandatory
    DESCRIPTION ""
    ::= { testmanager 4 }

  testData OBJECT-TYPE
    SYNTAX      INTEGER {
      random(0),
      ones(1),
      fox(2),
      graphic(3),
      text(4)
      }
    ACCESS      read-write
    STATUS      mandatory
    DESCRIPTION ""
    ::= { testmanager 5 }

  testEcc OBJECT-TYPE
    SYNTAX      INTEGER {
      v42bis(0),
      v42(1),
      none(2)
      }
    ACCESS      read-write
    STATUS      mandatory
    DESCRIPTION ""
    ::= { testmanager 6 }

  testEthernet OBJECT-TYPE
    SYNTAX      INTEGER {
      none(0),
      on(1)
      }
    ACCESS      read-write
    STATUS      mandatory
    DESCRIPTION ""
    ::= { testmanager 7 }



  --*************************************************************************
  --*************************************************************************
  --                              Installation
  --*************************************************************************
  --*************************************************************************

  installCountry OBJECT-TYPE
    SYNTAX      INTEGER {
      other(0),
      unitedStates(1),
      australia(2),
      canada(3),
      europeanUnion(4),
      france(5),
      germany(6)
      }
    ACCESS      read-write
    STATUS      mandatory
    DESCRIPTION "This object allows the user to specify the country that the
                 box lives in so we can change the way the box operates based
                 on local laws."
    ::= { installation 1 }



  --*************************************************************************
  --*************************************************************************
  --                              Frame Relay
  --*************************************************************************
  --*************************************************************************

  frameRelayTable OBJECT-TYPE
    SYNTAX      SEQUENCE OF FrameRelayEntry
    ACCESS      not-accessible
    STATUS      mandatory
    DESCRIPTION "Table of predefined frame relay virtual circuits."
    ::= { framerelay 1 }

  frameRelayEntry OBJECT-TYPE
    SYNTAX       FrameRelayEntry
    ACCESS       not-accessible
    STATUS       mandatory
    DESCRIPTION  "An entry in the table of predefined frame relay
                 virtual circuits."
    INDEX        { frameIFID, frameVCID }
    ::= { frameRelayTable 1 }

  FrameRelayEntry ::=
    SEQUENCE {
      frameIFID             Index,
      frameVCID             Index,
      frameIPAddr           IpAddress,
      frameEnableCongestion INTEGER,
      frameIPInterfaceNum   INTEGER
      }

  frameIFID OBJECT-TYPE
    SYNTAX      Index
    ACCESS      read-only
    STATUS      mandatory
    DESCRIPTION "The ifIndex Value of the ifEntry this virtual
                circuit is layered onto."
    ::= { frameRelayEntry 1 }

  frameVCID OBJECT-TYPE
    SYNTAX      Index
    ACCESS      read-only
    STATUS      mandatory
    DESCRIPTION "The Data Link Connection Identifier for this
                virtual circuit."
    ::= { frameRelayEntry 2 }

  frameIPAddr OBJECT-TYPE
    SYNTAX      IpAddress
    ACCESS      read-write
    STATUS      mandatory
    DESCRIPTION "The IP Address assigned to the virtual circuit."
    ::= { frameRelayEntry 3 }

  frameEnableCongestion OBJECT-TYPE
    SYNTAX      INTEGER {
      enable(0),
      disable(1)
      }
    ACCESS      read-write
    STATUS      mandatory
    DESCRIPTION "Enable or disable congestion tracking."
    ::= { frameRelayEntry 6 }

  frameIPInterfaceNum OBJECT-TYPE
    SYNTAX      INTEGER
    ACCESS      read-write
    STATUS      mandatory
    DESCRIPTION "The interface number assigned to a DLCI."
    ::= { frameRelayEntry 7 }

  --*************************************************************************
  --*************************************************************************
  --                           Frame Relay Stats
  --*************************************************************************
  --*************************************************************************

  framerelTable OBJECT-TYPE
    SYNTAX      SEQUENCE OF FramerelEntry
    ACCESS      not-accessible
    STATUS      mandatory
    DESCRIPTION "Table of frame relay statistics that
                 are not kept in the RFC."
    ::= { framerelay 2 }

  framerelEntry OBJECT-TYPE
    SYNTAX       FramerelEntry
    ACCESS       not-accessible
    STATUS       mandatory
    DESCRIPTION  "An entry of a link."
    INDEX        { framerelId }
    ::= { framerelTable 1 }

  FramerelEntry ::=
    SEQUENCE {
      framerelId                  Index,
      framerelRxNoBufferAvailable INTEGER,
      framerelRxDataOverflow      INTEGER,
      framerelRxMessageEnds       INTEGER,
      framerelRxPacketTooLong     INTEGER,
      framerelRxOverflow          INTEGER,
      framerelRxAbort             INTEGER,
      framerelRxBadCrc            INTEGER,
      framerelRxInvalidFrame      INTEGER,
      framerelTxUnderrun          INTEGER,
	    framerelTxOctets            INTEGER,
	    framerelRxOctets            INTEGER,
      framerelResets              INTEGER,
      framerelStatus              OCTET STRING
    }

  framerelId OBJECT-TYPE
    SYNTAX      Index
    ACCESS      read-write
    STATUS      mandatory
    DESCRIPTION "The link ID."
    ::= { framerelEntry 1 }

  framerelRxNoBufferAvailable OBJECT-TYPE
    SYNTAX      INTEGER
    ACCESS      read-only
    STATUS      mandatory
    DESCRIPTION "The number of packets received
               when no buffers were available."
    ::= { framerelEntry 2 }

  framerelRxDataOverflow OBJECT-TYPE
    SYNTAX      INTEGER
    ACCESS      read-only
    STATUS      mandatory
    DESCRIPTION "The number of packets received
  			 with overflow."
    ::= { framerelEntry 3 }

  framerelRxMessageEnds OBJECT-TYPE
    SYNTAX      INTEGER
    ACCESS      read-only
    STATUS      mandatory
    DESCRIPTION "The number of packets received
                 with message ends."
    ::= { framerelEntry 4 }

  framerelRxPacketTooLong OBJECT-TYPE
    SYNTAX      INTEGER
    ACCESS      read-only
    STATUS      mandatory
    DESCRIPTION "The number of packets received
                 that were tool long."
    ::= { framerelEntry 5 }

  framerelRxOverflow OBJECT-TYPE
    SYNTAX      INTEGER
    ACCESS      read-only
    STATUS      mandatory
    DESCRIPTION "The number of packets received
	                with overflow."
    ::= { framerelEntry 6 }

  framerelRxAbort OBJECT-TYPE
    SYNTAX      INTEGER
    ACCESS      read-only
    STATUS      mandatory
    DESCRIPTION "The number of packets received
                 that were aborted."
    ::= { framerelEntry 7 }

  framerelRxBadCrc OBJECT-TYPE
    SYNTAX      INTEGER
    ACCESS      read-only
    STATUS      mandatory
    DESCRIPTION "The number of packets received
                 that had bad CRC."
    ::= { framerelEntry 8 }

  framerelRxInvalidFrame OBJECT-TYPE
    SYNTAX      INTEGER
    ACCESS      read-only
    STATUS      mandatory
    DESCRIPTION "The number of packets received
                 that had an invalid frame."
    ::= { framerelEntry 9 }

  framerelTxUnderrun OBJECT-TYPE
    SYNTAX      INTEGER
    ACCESS      read-only
    STATUS      mandatory
    DESCRIPTION "The number of packets received
                 with underrun."
    ::= { framerelEntry 10 }

  framerelTxOctets OBJECT-TYPE
    SYNTAX      INTEGER
    ACCESS      read-only
    STATUS      mandatory
    DESCRIPTION "Tx bytes/second."
    ::= { framerelEntry 11 }

  framerelRxOctets OBJECT-TYPE
    SYNTAX      INTEGER
    ACCESS      read-only
    STATUS      mandatory
    DESCRIPTION "Rx bytes/second."
    ::= { framerelEntry 12 }

  framerelResets OBJECT-TYPE
    SYNTAX      INTEGER
    ACCESS      read-only
    STATUS      mandatory
    DESCRIPTION "Number of times LMI was reset."
    ::= { framerelEntry 13 }

  framerelStatus OBJECT-TYPE
    SYNTAX      OCTET STRING
    ACCESS      read-only
    STATUS      mandatory
    DESCRIPTION "LMI Link Status."
    ::= { framerelEntry 14 }

  --*************************************************************************
  -- Filter IP

  filterIpTable OBJECT-TYPE
    SYNTAX      SEQUENCE OF FilterIpEntry
    ACCESS      not-accessible
    STATUS      mandatory
    DESCRIPTION "Table of IP filter definitions."
    ::= { filterip 1 }

  filterIpEntry OBJECT-TYPE
    SYNTAX       FilterIpEntry
    ACCESS       not-accessible
    STATUS       mandatory
    DESCRIPTION  "An entry in the table of IP filter definitions."
    INDEX        { filterIpID }
    ::= { filterIpTable 1 }

  FilterIpEntry ::=
    SEQUENCE {
      filterIpID                     Index,
      filterIpName                   OCTET STRING,
      filterIpDirection              INTEGER,
      filterIpAction                 INTEGER,
      filterIpSourceIp               IpAddress,
      filterIpSourceMask             IpAddress,
      filterIpDestinationIp          IpAddress,
      filterIpDestinationMask        IpAddress,
      filterIpSourcePort             INTEGER,
      filterIpSourcePortCmp          FilterIpPortCmp,
      filterIpDestinationPort        INTEGER,
      filterIpDestinationPortCmp     FilterIpPortCmp,
      filterIpProtocol               INTEGER,
      filterIpTcpEstablished         INTEGER,
      filterIpDefaultDialin          INTEGER,
      filterIpSourceAddressCmp       FilterIpAddressCmp,
      filterIpDestinationAddressCmp  FilterIpAddressCmp,
      filterIpDefaultDialout         INTEGER
          }

  filterIpID OBJECT-TYPE
    SYNTAX      Index
    ACCESS      read-write
    STATUS      mandatory
    DESCRIPTION "The index used to identify this IP filter description
                 entry.  Indexes are continuous starting at one."
    ::= { filterIpEntry 1 }

  filterIpName OBJECT-TYPE
    SYNTAX      OCTET STRING
    ACCESS      read-write
    STATUS      mandatory
    DESCRIPTION "A name which can be used by other parts of the configuration
                 to identify and install this IP filter descriptino entry."
    ::= { filterIpEntry 2 }

  filterIpDirection OBJECT-TYPE
    SYNTAX      INTEGER {
      inactive(0),
      inbound(1),
      outbound(2),
      both(3)
      }
    ACCESS      read-write
    STATUS      mandatory
    DESCRIPTION "Specifies the direction of traffic to which this
                 filter is to be applied.  Setting the direction to
                 inactive will disable the filter without removing it."
    ::= { filterIpEntry 3 }

  filterIpAction OBJECT-TYPE
    SYNTAX      INTEGER {
      pass(0),
      block(1),
      wrap(2)
      }
    ACCESS      read-write
    STATUS      mandatory
    DESCRIPTION "Specified the action taken when this filter matches.
                 Blocking filters will cause the packet in question to
                 be dropped.  Passing filters will allow the packet
                 in question to proceed.  More than one filter may be
                 installed on an interface.  If any of the installed 
                 filters are passing type then the packet is required
                 to pass at least one of them.  Blocking filters
                 override passing filters.  Wrapping filters are 
                 processed last and will cause the original packet to
                 be wrapped with a new IP header and sent to the 
                 filterIpDestinationIp.  Wrapping works only on 
                 inbound before the packet gets to IP forwarding."
    ::= { filterIpEntry 4 }

  filterIpSourceIp OBJECT-TYPE
    SYNTAX      IpAddress
    ACCESS      read-write
    STATUS      mandatory
    DESCRIPTION "An IP address to match to the source IP address in 
                 the packet header."
    ::= { filterIpEntry 5 }

  filterIpSourceMask OBJECT-TYPE
    SYNTAX      IpAddress
    ACCESS      read-write
    STATUS      mandatory
    DESCRIPTION "A mask to use when comparing the source IP address.
                 Bit positions that are set to one will be compared
                 and zeros will be ignored.  Thus, a setting of 
                 0.0.0.0 will have the effect of disabling source
                 IP address comparision."
    ::= { filterIpEntry 6 }

  filterIpDestinationIp OBJECT-TYPE
    SYNTAX      IpAddress
    ACCESS      read-write
    STATUS      mandatory
    DESCRIPTION "An IP address to match to the destination IP address in 
                 the packet header."
    ::= { filterIpEntry 7 }

  filterIpDestinationMask OBJECT-TYPE
    SYNTAX      IpAddress
    ACCESS      read-write
    STATUS      mandatory
    DESCRIPTION "A mask to use when comparing the destination IP address.
                 Bit positions that are set to one will be compared
                 and zeros will be ignored.  Thus, a setting of 
                 0.0.0.0 will have the effect of disabling destination
                 IP address comparision."
    ::= { filterIpEntry 8 }

  filterIpSourcePort OBJECT-TYPE
    SYNTAX      INTEGER
    ACCESS      read-write
    STATUS      mandatory
    DESCRIPTION "A port number to use when comparing the source port."
    ::= { filterIpEntry 9 }

  filterIpSourcePortCmp OBJECT-TYPE
    SYNTAX      FilterIpPortCmp
    ACCESS      read-write
    STATUS      mandatory
    DESCRIPTION "What kind of comparison to do on the source port."
    ::= { filterIpEntry 10 }

  filterIpDestinationPort OBJECT-TYPE
    SYNTAX      INTEGER
    ACCESS      read-write
    STATUS      mandatory
    DESCRIPTION "A port number to use when comparing the destination port."
    ::= { filterIpEntry 11 }

  filterIpDestinationPortCmp OBJECT-TYPE
    SYNTAX      FilterIpPortCmp
    ACCESS      read-write
    STATUS      mandatory
    DESCRIPTION "What kind of comparison to do on the destination port."
    ::= { filterIpEntry 12 }

  filterIpProtocol OBJECT-TYPE
    SYNTAX      INTEGER
    ACCESS      read-write
    STATUS      mandatory
    DESCRIPTION "A protocol to match to the protocol in the IP header.
                 A setting of 0 disables the comparison.  Any integer
                 may be set, the enumerations are for convenience."
    ::= { filterIpEntry 13 }

  filterIpTcpEstablished OBJECT-TYPE
    SYNTAX      INTEGER {
      anyPackets(0),
      onlyEstablishedConnections(1)
      }
    ACCESS      read-write
    STATUS      mandatory
    DESCRIPTION "The filter can be chossen to match only those packets
                 which indicate in the TCP header flags that the
                 connection is established."
    ::= { filterIpEntry 14 }

  filterIpDefaultDialin OBJECT-TYPE
    SYNTAX      INTEGER {
      no(0),
      applyToDialin(1)
      }
    ACCESS      read-write
    STATUS      mandatory
    DESCRIPTION "The filter can be chossen to be a default which will
                 be applied to all dialin users in the case that the
                 authentication of the dialin user does not 
                 specifically specify any filters."
    ::= { filterIpEntry 15 }

  filterIpSourceAddressCmp OBJECT-TYPE
    SYNTAX      FilterIpAddressCmp
    ACCESS      read-write
    STATUS      mandatory
    DESCRIPTION "An IP address to match to the source IP address in 
                 the packet header."
    ::= { filterIpEntry 16 }

  filterIpDestinationAddressCmp OBJECT-TYPE
    SYNTAX      FilterIpAddressCmp
    ACCESS      read-write
    STATUS      mandatory
    DESCRIPTION "An IP address to match to the destination IP address in 
                 the packet header."
    ::= { filterIpEntry 17 }

  filterIpDefaultDialout OBJECT-TYPE
    SYNTAX      INTEGER {
      no(0),
      applyToDialout(1)
      }
    ACCESS      read-write
    STATUS      mandatory
    DESCRIPTION "The filter can be chossen to be a default which will
                 be applied to all dialout users."
    ::= { filterIpEntry 18 }


  --*************************************************************************
  -- General Routing Table

  genRouteTable OBJECT-TYPE
    SYNTAX  SEQUENCE OF GenRouteEntry
    ACCESS  not-accessible
    STATUS  mandatory
    DESCRIPTION
	       "A table of all routes (active or not) held in the
          general routing table of the device.  This is a 
          larger more flexible implementation of the MIB-II
          forwarding table, not limited by the destination
          only indexing."
    ::= { genroute 1 }

  genRouteEntry OBJECT-TYPE
    SYNTAX  GenRouteEntry
    ACCESS  not-accessible
    STATUS  mandatory
    DESCRIPTION
            "A single route entry in the table designating a
             destination and the protocol which has offered a
             gateway to that desintation."
    INDEX   { genRouteDest, genRouteProto }
    ::= { genRouteTable 1 }

  GenRouteEntry ::=
    SEQUENCE {
      genRouteDest    IpAddress,
      genRouteMask    IpAddress,
      genRouteProto   INTEGER,
      genRouteState   INTEGER,
      genRouteGateway IpAddress,
      genRouteIfIndex INTEGER,
      genRouteCost    INTEGER,
      genRouteAge     INTEGER,
      genRouteTag     INTEGER
      }

  genRouteDest OBJECT-TYPE
    SYNTAX  IpAddress
    ACCESS  read-write
    STATUS  mandatory
    DESCRIPTION
             "The destination IP address of this route.  An
              entry with a value of 0.0.0.0 is considered a
              default route.  Multiple routes to a single
              destination can appear in the table."
    ::= { genRouteEntry 1 }

  genRouteMask OBJECT-TYPE
    SYNTAX  IpAddress
    ACCESS  read-write
    STATUS  mandatory
    DESCRIPTION
             "This is the subnet mask which is logically ANDed
              with the destination IP address to determine if
              an outbound packet can be serviced by this route.
              During row creation in this routing table if this
              field is not provided it will be created based on
              the internet standard classes: A, B, and C."
  ::= { genRouteEntry 2 }

  genRouteProto OBJECT-TYPE
    SYNTAX  INTEGER {
      unknown(0),
      local(1),
      user(2),
      ospf(3),
      rip(4),
      icmp(5),
      radius(6),
      ospfInter(8),
      ospfInterTransit(9),
      ospfExternType1(10),
      ospfExternType2(11),
      ospfIntra1(12),
      ospfIntra2(13),
      ospfIntra3(14)
      }
    ACCESS  read-only
    STATUS  mandatory
    DESCRIPTION
             "This object defines the mechanism by which this route was
              learned.  The following are defined:
                user      Added through row creation in this MIB
                local     Added by O/S to support an interface
                icmp      Added by reception of an ICMP packet
                rip       Added by reception of a RIP packet
                radius    Provided in a RADIUS response packet"
    ::= { genRouteEntry 3 }

  genRouteState OBJECT-TYPE
    SYNTAX  INTEGER {
      invalid(1),
      active(2),
      nopath(3),
      agedout(4),
      costly(5)
      }
    ACCESS  read-write
    STATUS  mandatory
    DESCRIPTION
             "This object defines the staes which a route may be in
              during its life time:
                invalid   Setting this will remove the route
                active    Valid route in use with the lowest cost
                saved     Valid route not in use due to higher cost
                agedout   Invalid route soon to be removed"
    ::= { genRouteEntry 4 }

  genRouteGateway OBJECT-TYPE
    SYNTAX  IpAddress
    ACCESS  read-write
    STATUS  mandatory
    DESCRIPTION
             "This specifies the IP to which the packets should
              be forwarded.  In the case of a route bound to an
              interface this value will be zero."
    ::= { genRouteEntry 5 }

  genRouteIfIndex OBJECT-TYPE
    SYNTAX  INTEGER
    ACCESS  read-write
    STATUS  mandatory
    DESCRIPTION
             "The index value which uniquely identifies the
              local interface through which the next hop of this
              route should be reached.  This may be zero in the
              case that the routeis not active or no interface
              could be found which has access to the gateway."
    ::= { genRouteEntry 6 }

  genRouteCost OBJECT-TYPE
    SYNTAX  INTEGER
    ACCESS  read-write
    STATUS  mandatory
    DESCRIPTION
            "This is the cost of the route as defined by RIP
             standards.  Cost is sometimes considered to be
             the number of hops.  A cost of 16 is considered
             to be infinite.  A cost can be give to user
             entered routes so that their preference in relation
             to learned routes can be calculated."
    ::= { genRouteEntry 7 }

  genRouteAge OBJECT-TYPE
    SYNTAX  INTEGER
    ACCESS  read-only
    STATUS  mandatory
    DESCRIPTION
             "The number of seconds since this route was last
              updated or otherwise determined to be correct.
              Note that no semantics of `too old' can be implied
              except through knowledge of the routing protocol
              by which the route was learned."
  ::= { genRouteEntry 8 }

  genRouteTag OBJECT-TYPE
    SYNTAX  INTEGER
    ACCESS  read-only
    STATUS  mandatory
    DESCRIPTION
             "An identifier associated with the route.  This can 
              have different meaning depending on the protocol.
              For learned RIP routes this gives the tag that was
              passed with the route.  For radius routes this 
              provides the session ID of the call."
  ::= { genRouteEntry 9 }

  --*************************************************************************
  -- DAX (Digital Cross Connect) Clocking and PCM Routing tables.
  --   An understanding of the H.110 PCM Highway mechanims is sugested.
  GSDSLDaxReferenceType ::= INTEGER {
                 wan-1(1),
                 wan-2(2),
                 wan-3(3),
                 wan-4(4),
                 wan-5(5),
                 wan-6(6),
                 wan-7(7),
                 wan-8(8),
                 wan-9(9),
                 wan-10(10),
                 wan-11(11),
                 wan-12(12),
                 wan-13(13),
                 wan-14(14),
                 wan-15(15),
                 wan-16(16),
                 internal(200),
                 system(500)
                 }

  
  MDSLDaxReferenceType ::= INTEGER {
                 none(0),
                 wan-1(1),
                 wan-2(2),
                 wan-3(3),
                 wan-4(4),
                 wan-5(5),
                 wan-6(6),
                 wan-7(7),
                 wan-8(8),
                 wan-9(9),
                 wan-10(10),
                 wan-11(11),
                 wan-12(12),
                 wan-13(13),
                 wan-14(14),
                 wan-15(15),
                 wan-16(16),
                 mdsl-1(51),
                 mdsl-2(52),
                 mdsl-3(53),
                 mdsl-4(54),
                 mdsl-5(55),
                 mdsl-6(56),
                 mdsl-7(57),
                 mdsl-8(58),
                 mdsl-9(59),
                 mdsl-10(60),
                 mdsl-11(61),
                 mdsl-12(62),
                 mdsl-13(63),
                 mdsl-14(64),
                 mdsl-15(65),
                 mdsl-16(66),
                 internal(200),
                 external(300)
                 }


  DaxReferenceTypeNoDSL ::= INTEGER {
                 none(0),
                 wan-1(1),
                 wan-2(2),
                 wan-3(3),
                 wan-4(4),
                 wan-5(5),
                 wan-6(6),
                 wan-7(7),
                 wan-8(8),
                 wan-9(9),
                 wan-10(10),
                 wan-11(11),
                 wan-12(12),
                 wan-13(13),
                 wan-14(14),
                 wan-15(15),
                 wan-16(16),
                 internal(200),
                 external(300)
                 }


  DaxReferenceType ::= INTEGER {
                 none(0),
                 wan-1(1),
                 wan-2(2),
                 wan-3(3),
                 wan-4(4),
                 wan-5(5),
                 wan-6(6),
                 wan-7(7),
                 wan-8(8),
                 wan-9(9),
                 wan-10(10),
                 wan-11(11),
                 wan-12(12),
                 wan-13(13),
                 wan-14(14),
                 wan-15(15),
                 wan-16(16),
                 netref-1(101),
                 netref-2(102),
                 internal(200),
                 external(300)
                 }

  DaxM6511ReferenceType ::= INTEGER {
                 none(0),
                 wan-1(1),
                 internal(200),
                 h110-pub-netref1(600),
                 h110-pub-netref2(601),
                 h110-loc-netref1(602),
                 h110-loc-netref2(603),
                 h110-internal(604)                 
                 }

  T1E1DaxReferenceType ::= INTEGER {
                 none(0),
                 wan-1(1),
                 wan-2(2),
                 wan-3(3),
                 wan-4(4),
                 internal(200),
                 external(300)
                 }
  
  
  T1E1DaxDeviceNumberType ::= INTEGER {
                 port1(1),   port2(2),   port3(3),   port4(4),
                 port5(5),   port6(6),   port7(7),   port8(8),   port9(9),
                 port10(10), port11(11), port12(12), port13(13), port14(14),
                 port15(15), port16(16)
                 }

  T1E1DaxM6511DeviceNumberType ::= INTEGER {
                 port1(1),   port2(2),   port3(3),   port4(4),
                 port5(5),   port6(6),   port7(7),   port8(8),   port9(9),
                 port10(10), port11(11), port12(12), port13(13), port14(14),
                 port15(15), port16(16), port17(17), port18(18), port19(19),
                 port20(20), port21(21), port22(22), port23(23), port24(24),
                 port25(25), port26(26), port27(27), port28(28), port29(29),
                 port30(30), port31(31), port32(32), port33(33), port34(34),
                 port35(35), port36(36), port37(37), port38(38), port39(39),
                 port40(40), port41(41), port42(42), port43(43), port44(44),
                 port45(45), port46(46), port47(47), port48(48), port49(49),
                 port50(50), port51(51), port52(52), port53(53), port54(54),
                 port55(55), port56(56), port57(57), port58(58), port59(59),
                 port60(60), port61(61), port62(62), port63(63), port64(64),
                 port65(65), port66(66), port67(67), port68(68), port69(69),
                 port70(70), port71(71), port72(72), port73(73), port74(74),
                 port75(75), port76(76), port77(77), port78(78), port79(79),
                 port80(80), port81(81), port82(82), port83(83), port84(84)
                 }

  MDSLDaxDeviceNumberType ::= INTEGER {
                 port1(1),   port2(2),   port3(3),   port4(4),
                 port5(5),   port6(6),   port7(7),   port8(8),   port9(9),
                 port10(10), port11(11), port12(12), port13(13), port14(14),
                 port15(15), port16(16)
                 }

  DaxDeviceNumberType ::= INTEGER {
                 port1(1),   port2(2),   port3(3),   port4(4),
                 port5(5),   port6(6),   port7(7),   port8(8),   port9(9),
                 port10(10), port11(11), port12(12), port13(13), port14(14),
                 port15(15), port16(16), port17(17), port18(18), port19(19),
                 port20(20), port21(21), port22(22), port23(23), port24(24)
                 }

  GSDSLDaxDeviceNumberType ::= INTEGER {
                 port1(1),   port2(2),   port3(3),   port4(4),
                 port5(5),   port6(6),   port7(7),   port8(8),   port9(9),
                 port10(10), port11(11), port12(12), port13(13), port14(14),
                 port15(15), port16(16)
                 }

  GSDSLDaxDeviceStreamType ::= INTEGER {
                 port1(1),   port2(2),   port3(3),   port4(4),
                 port5(5),   port6(6),   port7(7),   port8(8),   port9(9),
                 port10(10), port11(11), port12(12), port13(13), port14(14),
                 port15(15), port16(16), port17(17), port18(18), port19(19),
                 port20(20), port21(21), port22(22), port23(23), port24(24),
                 port25(25), port26(26), port27(27), port28(28), port29(29),
                 port30(30), port31(31), port32(32)
                 }

  daxClockTable OBJECT-TYPE
    SYNTAX  SEQUENCE OF DaxClockEntry
    ACCESS  not-accessible
    STATUS  mandatory
    DESCRIPTION
	          ""
    ::= { dax 1 }

  daxClockEntry OBJECT-TYPE
    SYNTAX  DaxClockEntry
    ACCESS  not-accessible
    STATUS  mandatory
    DESCRIPTION
            "A single entry in the table designating a circuit and
             the clock signals used for that circuit."
    INDEX   { daxClockCircuit }
    ::= { daxClockTable 1 }

  DaxClockEntry ::=
    SEQUENCE {
      daxClockCircuit             Index,
      daxClockMode                INTEGER,
      daxClockMainRef             DaxReferenceType,
      daxClockFallbackRef         DaxReferenceType,
      daxM6511ClockMainRef        DaxM6511ReferenceType,
      daxM6511ClockFallbackRef    DaxM6511ReferenceType,
      daxClockFailure             INTEGER,
      t1e1daxClockMainRef         T1E1DaxReferenceType,
      t1e1daxClockFallbackRef     T1E1DaxReferenceType
      }

  daxClockCircuit OBJECT-TYPE
    SYNTAX  Index
    ACCESS  read-only
    STATUS  mandatory
    DESCRIPTION
             "An index which identifies each serarate digital cross
              connect circuit.  Used as an index into this table."
    ::= { daxClockEntry 1 }

  daxClockMode OBJECT-TYPE
    SYNTAX  INTEGER {
      master(1),
      secondary(2),
      slave(3)
      }
    ACCESS  read-write
    STATUS  mandatory
    DESCRIPTION
             "Designated this circuits roll in the overall clocking
              scheme of the entire system.  The master devide is
              responsible for providing the system clock in synchronization
              with one of his references.  The secondary does this same job
              in the absense of the master.  The slaves simply listen to
              the system clock, but may provide a reference for use by
              the master."
    ::= { daxClockEntry 2 }

  daxClockMainRef OBJECT-TYPE
    SYNTAX  DaxReferenceType
    ACCESS  read-write
    STATUS  mandatory
    DESCRIPTION
             "Master: This defines the clock source from which the system
              will base its timing.  Secondary: This defines the clock source
              from which the system will base its timing in the event of
              a complete failure of the master.  Slave: This defines the 
              clock source which will be driven to the NETREF #1."
    ::= { daxClockEntry 3 }

  daxClockFallbackRef OBJECT-TYPE
    SYNTAX  DaxReferenceType
    ACCESS  read-write
    STATUS  mandatory
    DESCRIPTION
             "Master: This defines the clock source from which the system
              will base its timing if the MainRef goes bad.  Secondary: not used.
              Slave: This defines the clock source which will be driven to
              the NETREF #2."
    ::= { daxClockEntry 4 }

  daxClockFailure OBJECT-TYPE
    SYNTAX  INTEGER {
      no-failures(0),
      main-ref-fail(1),
      fallback-ref-fail(2),
      master-system-clock-fail(4),
      secondary-system-clock-fail(8)
      }
    ACCESS  read-write
    STATUS  mandatory
    DESCRIPTION
             "Identifies which clock this circuit has detected as failed. A
              clock is failed if transissions are not seen, or if the
              number of clocks per frame period is not correct.  In some
              cases the failure is actually a detection of LOS on the WAN
              interface used for the reference.  This is bit enumerated."
    ::= { daxClockEntry 5 }

  t1e1daxClockMainRef OBJECT-TYPE
    SYNTAX  T1E1DaxReferenceType
    ACCESS  read-write
    STATUS  mandatory
    DESCRIPTION
             "Master: This defines the clock source from which the system
              will base its timing.  Secondary: This defines the clock source
              from which the system will base its timing in the event of
              a complete failure of the master.  Slave: This defines the 
              clock source which will be driven to the NETREF #1."
    ::= { daxClockEntry 6 }

  t1e1daxClockFallbackRef OBJECT-TYPE
    SYNTAX  T1E1DaxReferenceType
    ACCESS  read-write
    STATUS  mandatory
    DESCRIPTION
             "Master: This defines the clock source from which the system
              will base its timing if the MainRef goes bad.  Secondary: not used.
              Slave: This defines the clock source which will be driven to
              the NETREF #2."
    ::= { daxClockEntry 7 }

daxM6511ClockMainRef OBJECT-TYPE
    SYNTAX  DaxM6511ReferenceType
    ACCESS  read-only
    STATUS  mandatory
    DESCRIPTION
             "Master: This defines the clock source from which the system
              will base its timing.  Secondary: This defines the clock source
              from which the system will base its timing in the event of
              a complete failure of the master.  Slave: This defines the 
              clock source which will be driven to the NETREF #1."
    ::= { daxClockEntry 8 }

  daxM6511ClockFallbackRef OBJECT-TYPE
    SYNTAX  DaxM6511ReferenceType
    ACCESS  read-only
    STATUS  mandatory
    DESCRIPTION
             "Master: This defines the clock source from which the system
              will base its timing if the MainRef goes bad.  Secondary: not used.
              Slave: This defines the clock source which will be driven to
              the NETREF #2."
    ::= { daxClockEntry 9 }
    
  daxConnectionTable OBJECT-TYPE
    SYNTAX  SEQUENCE OF DaxConnectionEntry
    ACCESS  not-accessible
    STATUS  mandatory
    DESCRIPTION
	          ""
    ::= { dax 2 }

  daxConnectionEntry OBJECT-TYPE
    SYNTAX  DaxConnectionEntry
    ACCESS  not-accessible
    STATUS  mandatory
    DESCRIPTION
            "A single entry in the table designating a connection 
             from a single interface o another interface"
    INDEX   { daxConnectionID }
    ::= { daxConnectionTable 1 }

  DaxConnectionEntry ::=
    SEQUENCE {
      daxConnectionID               Index,
      daxDeviceTypeToiDSL           INTEGER,
      daxDeviceNumberTo             DaxDeviceNumberType,
      daxDeviceSlotTo               OCTET STRING,
      daxDeviceTypeFromiDSL         INTEGER,
      daxDeviceNumberFrom           DaxDeviceNumberType,
      daxDeviceSlotFrom             OCTET STRING,
      daxConnectionDirection        INTEGER,
      daxConnectionStatus           INTEGER,
      daxCliString                  OCTET STRING,
      daxDeviceTypeTomDSL           INTEGER,
      daxDeviceTypeFrommDSL         INTEGER,
      daxDeviceNumberTomDSL         MDSLDaxDeviceNumberType,
      daxDeviceNumberFrommDSL       MDSLDaxDeviceNumberType,
      daxDeviceTypeToT1E1           INTEGER,
      daxDeviceTypeFromT1E1         INTEGER,
      daxDeviceNumberToT1E1         T1E1DaxDeviceNumberType,
      daxDeviceNumberFromT1E1       T1E1DaxDeviceNumberType,
                                    
      daxDeviceTypeToGsDSL          INTEGER,
      daxDeviceTypeFromGsDSL        INTEGER,
      daxDeviceNumberToGsDSL        GSDSLDaxDeviceNumberType,
      daxDeviceNumberFromGsDSL      GSDSLDaxDeviceStreamType,
                                    
      daxDeviceTypeRxGsDSL          INTEGER,
      daxDeviceNumberRxGsDSL        GSDSLDaxDeviceStreamType,
      daxDeviceSlotRxGsDSL          OCTET STRING,
                                    
      daxFallbackTypeTo             INTEGER,
      daxFallbackNumberTo           DaxDeviceNumberType,
      daxFallbackSlotTo             OCTET STRING,
      daxFallbackTypeFrom           INTEGER,
      daxFallbackNumberFrom         DaxDeviceNumberType,
      daxFallbackSlotFrom           OCTET STRING,
      daxBackupAvailable            INTEGER,
                                    
      daxBackupAlarm                INTEGER,
      daxMappingRecovery            INTEGER,
      daxForceRecovery              INTEGER,
      daxFallbackCliString          OCTET STRING,
                                    
      daxNewMapTypeTo               INTEGER,
      daxNewMapNumberTo             GSDSLDaxDeviceNumberType,
                                    
      daxNewMapTypeFrom             INTEGER,
      daxNewMapNumberFrom           GSDSLDaxDeviceStreamType,
                                    
      daxNewMapTypeH110             INTEGER,
      daxNewMapNumberH110           GSDSLDaxDeviceStreamType,
      daxNewMapSlotH110             OCTET STRING,

      daxM6511DeviceNumberToT1E1    T1E1DaxM6511DeviceNumberType,
      daxM6511DeviceNumberFromT1E1  T1E1DaxM6511DeviceNumberType,

      daxM6511Tug3Number            INTEGER,
      daxM6511Au3Number             INTEGER,
      daxM6511Tug2Number            INTEGER,
      daxM6511Tu12Number            INTEGER
    }

  daxConnectionID OBJECT-TYPE
    SYNTAX  Index
    ACCESS  read-write
    STATUS  mandatory
    DESCRIPTION
             "An index into the connection table."
    ::= { daxConnectionEntry 1 }

  daxDeviceTypeToiDSL OBJECT-TYPE
    SYNTAX  INTEGER {
      none(0),
      t1-e1(1),
      iDSL(2)
      }
    ACCESS  read-write
    STATUS  mandatory
    DESCRIPTION
             "Setting this variable will determine one of the interface types
              used in making the dax connection. The other interface will be 
              specified using the deviceTypeFrom"
    ::= { daxConnectionEntry 2 }

  daxDeviceNumberTo OBJECT-TYPE
    SYNTAX  DaxDeviceNumberType
    ACCESS  read-write
    STATUS  mandatory
    DESCRIPTION
             "After selecting the device type, this number will determine which device 
              in the bank will be used."
    ::= { daxConnectionEntry 3 }

  daxDeviceSlotTo OBJECT-TYPE
    SYNTAX  OCTET STRING (SIZE (0..40))
    ACCESS  read-write
    STATUS  mandatory
    DESCRIPTION
             "This variable is used to specify the range of slots to be used 
              in the connection. The following notation will be used
              1) a dash  (-) will be used to specify a range of slots i.e. 5 - 7
              2) a comma (,) will be used to specify non-contiguous slots 5,8,15
              to speficy slots 1,2,3,4,7,15,16, and 17 use the following notation
              1-4,7,15 - 17
              NOTE: The total number of slots specified here must match the total 
              number of slots specified in the daxDeviceSlotFrom variable"
    ::= { daxConnectionEntry 4 }


  daxDeviceTypeFromiDSL OBJECT-TYPE
    SYNTAX  INTEGER {
      none(0),
      t1-e1(1),
      iDSL(2),
      toH110(5)
      }
    ACCESS  read-write
    STATUS  mandatory
    DESCRIPTION
             "Setting this variable will determine one of the interface types
              used in making the dax connection. The other interface will be 
              specified using the deviceTypeTo"
    ::= { daxConnectionEntry 5 }

  daxDeviceNumberFrom OBJECT-TYPE
    SYNTAX  DaxDeviceNumberType
    ACCESS  read-write
    STATUS  mandatory
    DESCRIPTION
             "After selecting the device type, this number will determine which device 
              in the bank will be used."
    ::= { daxConnectionEntry 6 }

  daxDeviceSlotFrom OBJECT-TYPE
    SYNTAX  OCTET STRING (SIZE (0..40))
    ACCESS  read-write
    STATUS  mandatory
    DESCRIPTION
             "This variable is used to specify the range of slots to be used 
              in the connection. The following notation will be used
              1) a dash  (-) will be used to specify a range of slots i.e. 5 - 7
              2) a comma (,) will be used to specify non-contiguous slots 5,8,15
              to speficy slots 1,2,3,4,7,15,16, and 17 use the following notation
              1-4,7,15 - 17. 
              NOTE: The total number of slots specified here must match the total 
              number of slots specified in the deviceSlotTo variable"
    ::= { daxConnectionEntry 7 }


  daxConnectionDirection OBJECT-TYPE
    SYNTAX  INTEGER {
      to-from(0),
      from-to(1),
      bi-directional(2),
      selfLoop(3)
      }
    ACCESS  read-write
    STATUS  mandatory
    DESCRIPTION
             "Setting this variable will determine one of the interface types
              used in making the dax connection. The other interface will be 
              specified using the deviceTypeTo"
    ::= { daxConnectionEntry 8 }

  daxConnectionStatus OBJECT-TYPE
    SYNTAX  INTEGER {
      active(0),
      delete(1)
      }
    ACCESS  read-write
    STATUS  mandatory
    DESCRIPTION
             "This variable can be used to activate a connection, deactivate 
              a connection, or delete a connection from the box. if a 
              connection is deactivated the information will be stored in the 
              box but the connection will not be available to pass data."
    ::= { daxConnectionEntry 9 }

  daxCliString OBJECT-TYPE
    SYNTAX  OCTET STRING (SIZE (0..200))
    ACCESS  read-only
    STATUS  mandatory
    DESCRIPTION
             "Connection description in the cli format"
    ::= { daxConnectionEntry 10 }

  daxDeviceTypeTomDSL OBJECT-TYPE
    SYNTAX  INTEGER {
      t1-e1(1),
      mDSL(3)
      }
    ACCESS  read-write
    STATUS  mandatory
    DESCRIPTION
             "Setting this variable will determine one of the interface types
              used in making the dax connection. The other interface will be 
              specified using the deviceTypeFrom"
    ::= { daxConnectionEntry 11 }

  daxDeviceTypeFrommDSL OBJECT-TYPE
    SYNTAX  INTEGER {
      t1-e1(1),
      mDSL(3)
      }
    ACCESS  read-write
    STATUS  mandatory
    DESCRIPTION
             "Setting this variable will determine one of the interface types
              used in making the dax connection. The other interface will be 
              specified using the deviceTypeTo"
    ::= { daxConnectionEntry 12 }

  daxDeviceNumberTomDSL OBJECT-TYPE
    SYNTAX  MDSLDaxDeviceNumberType
    ACCESS  read-write
    STATUS  mandatory
    DESCRIPTION
             "After selecting the device type, this number will determine which device 
              in the bank will be used."
    ::= { daxConnectionEntry 15 }

  daxDeviceNumberFrommDSL OBJECT-TYPE
    SYNTAX  MDSLDaxDeviceNumberType
    ACCESS  read-write
    STATUS  mandatory
    DESCRIPTION
             "After selecting the device type, this number will determine which device 
              in the bank will be used."
    ::= { daxConnectionEntry 16 }

  daxDeviceTypeToT1E1 OBJECT-TYPE
    SYNTAX  INTEGER {
      none(0),
      t1-e1(1)
      }
    ACCESS  read-write
    STATUS  mandatory
    DESCRIPTION
             "Setting this variable will determine the interface types
              used in making the dax connection. The other interface will be 
              specified using the deviceTypeFrom"
    ::= { daxConnectionEntry 17 }

  daxDeviceTypeFromT1E1 OBJECT-TYPE
    SYNTAX  INTEGER {
      none(0),
      t1-e1(1),
      toH110(5)
      }
    ACCESS  read-write
    STATUS  mandatory
    DESCRIPTION
             "Setting this variable will determine one of the interface types
              used in making the dax connection. The other interface will be 
              specified using the deviceTypeTo"
    ::= { daxConnectionEntry 18 }

  daxDeviceNumberToT1E1 OBJECT-TYPE
    SYNTAX  T1E1DaxDeviceNumberType
    ACCESS  read-write
    STATUS  mandatory
    DESCRIPTION
             "After selecting the device type, this number will determine which device 
              in the bank will be used."
    ::= { daxConnectionEntry 19 }

  daxDeviceNumberFromT1E1 OBJECT-TYPE
    SYNTAX  T1E1DaxDeviceNumberType
    ACCESS  read-write
    STATUS  mandatory
    DESCRIPTION
             "After selecting the device type, this number will determine which device 
              in the bank will be used."
    ::= { daxConnectionEntry 20 }


--************************************************************************************
-- added for the 3096RC development
--************************************************************************************
  daxDeviceTypeToGsDSL OBJECT-TYPE
    SYNTAX  INTEGER {
      none(0),
      t1-e1(1),
      gsdsl(4)
      }
    ACCESS  read-write
    STATUS  mandatory
    DESCRIPTION
             ""
    ::= { daxConnectionEntry 21 }

  daxDeviceTypeFromGsDSL OBJECT-TYPE
    SYNTAX  INTEGER {
      none(0),
      t1-e1(1),
      gsdsl(4),
      toH110(5)
      }
    ACCESS  read-write
    STATUS  mandatory
    DESCRIPTION
             ""
    ::= { daxConnectionEntry 22 }

  daxDeviceNumberToGsDSL OBJECT-TYPE
    SYNTAX  GSDSLDaxDeviceNumberType
    ACCESS  read-write
    STATUS  mandatory
    DESCRIPTION
             ""
    ::= { daxConnectionEntry 23 }

  daxDeviceNumberFromGsDSL OBJECT-TYPE
    SYNTAX  GSDSLDaxDeviceStreamType
    ACCESS  read-write
    STATUS  mandatory
    DESCRIPTION
             ""
    ::= { daxConnectionEntry 24 }

  daxDeviceTypeRxGsDSL OBJECT-TYPE
    SYNTAX  INTEGER {
      none(0),
      fromH110(6)
      }
    ACCESS  read-write
    STATUS  mandatory
    DESCRIPTION
             ""
    ::= { daxConnectionEntry 25 }

  daxDeviceNumberRxGsDSL OBJECT-TYPE
    SYNTAX  GSDSLDaxDeviceStreamType
    ACCESS  read-write
    STATUS  mandatory
    DESCRIPTION
             ""
    ::= { daxConnectionEntry 26 }

  daxDeviceSlotRxGsDSL      OBJECT-TYPE
    SYNTAX  OCTET STRING (SIZE (0..40))
    ACCESS  read-write
    STATUS  mandatory
    DESCRIPTION
             "This variable is used to specify the range of slots to be used 
              in the connection. The following notation will be used
              1) a dash  (-) will be used to specify a range of slots i.e. 5 - 7
              2) a comma (,) will be used to specify non-contiguous slots 5,8,15
              to speficy slots 1,2,3,4,7,15,16, and 17 use the following notation
              1-4,7,15 - 17. 
              NOTE: The total number of slots specified here must match the total 
              number of slots specified in the deviceSlotTo variable"
    ::= { daxConnectionEntry 27 }


  daxFallbackTypeTo  OBJECT-TYPE
    SYNTAX  INTEGER {
      t1-e1(1),
      iDSL(2)
      }
    ACCESS  read-only
    STATUS  mandatory
    DESCRIPTION
             ""
    ::= { daxConnectionEntry 28 }

  daxFallbackNumberTo  OBJECT-TYPE
    SYNTAX  DaxDeviceNumberType
    ACCESS  read-only
    STATUS  mandatory
    DESCRIPTION
             ""
    ::= { daxConnectionEntry 29 }

  daxFallbackSlotTo OBJECT-TYPE
    SYNTAX  OCTET STRING (SIZE (0..40))
    ACCESS  read-only
    STATUS  mandatory
    DESCRIPTION
             "This variable is used to specify the range of slots to be used 
              in the connection. The following notation will be used
              1) a dash  (-) will be used to specify a range of slots i.e. 5 - 7
              2) a comma (,) will be used to specify non-contiguous slots 5,8,15
              to speficy slots 1,2,3,4,7,15,16, and 17 use the following notation
              1-4,7,15 - 17
              NOTE: The total number of slots specified here must match the total 
              number of slots specified in the daxDeviceSlotFrom variable"
    ::= { daxConnectionEntry 30 }

  daxFallbackTypeFrom OBJECT-TYPE
    SYNTAX  INTEGER {
      t1-e1(1),
      iDSL(2)
      }
    ACCESS  read-only
    STATUS  mandatory
    DESCRIPTION
             ""
    ::= { daxConnectionEntry 31 }

  daxFallbackNumberFrom OBJECT-TYPE
    SYNTAX  DaxDeviceNumberType
    ACCESS  read-only
    STATUS  mandatory
    DESCRIPTION
             ""
    ::= { daxConnectionEntry 32 }

  daxFallbackSlotFrom OBJECT-TYPE
    SYNTAX  OCTET STRING (SIZE (0..40))
    ACCESS  read-only
    STATUS  mandatory
    DESCRIPTION
             "This variable is used to specify the range of slots to be used 
              in the connection. The following notation will be used
              1) a dash  (-) will be used to specify a range of slots i.e. 5 - 7
              2) a comma (,) will be used to specify non-contiguous slots 5,8,15
              to speficy slots 1,2,3,4,7,15,16, and 17 use the following notation
              1-4,7,15 - 17
              NOTE: The total number of slots specified here must match the total 
              number of slots specified in the daxDeviceSlotFrom variable"
    ::= { daxConnectionEntry 33 }

  daxBackupAvailable OBJECT-TYPE
    SYNTAX  INTEGER {
      notAvailable(0),
      available(1)
      }
    ACCESS  read-only
    STATUS  mandatory
    DESCRIPTION
             ""
    ::= { daxConnectionEntry 34 }

  daxBackupAlarm  OBJECT-TYPE
    SYNTAX  INTEGER {
      noAlarmActive(0),
      alarmActive(1)
      }
    ACCESS  read-only
    STATUS  mandatory
    DESCRIPTION
             ""
    ::= { daxConnectionEntry 35 }

  daxMappingRecovery  OBJECT-TYPE
    SYNTAX  INTEGER {
      userForceRecovery(0),
      autoRecovery(1)
      }
    ACCESS  read-write
    STATUS  mandatory
    DESCRIPTION
             ""
    ::= { daxConnectionEntry 36 }

  daxForceRecovery  OBJECT-TYPE
    SYNTAX  INTEGER {
      noOperation(0),
      forceRecovery(1)
      }
    ACCESS  read-write
    STATUS  mandatory
    DESCRIPTION
             ""
    ::= { daxConnectionEntry 37 }

  
  daxFallbackCliString OBJECT-TYPE
    SYNTAX  OCTET STRING (SIZE (0..200))
    ACCESS  read-only
    STATUS  mandatory
    DESCRIPTION
             "Connection description in the cli format"
    ::= { daxConnectionEntry 38 }

  daxNewMapTypeTo OBJECT-TYPE
    SYNTAX  INTEGER {
      none(0),
      t1-e1(1),
      iDSL(2),
      gsdsl(4)
      }
    ACCESS  read-only
    STATUS  mandatory
    DESCRIPTION
             ""
    ::= { daxConnectionEntry 39 }

  daxNewMapNumberTo OBJECT-TYPE
    SYNTAX  GSDSLDaxDeviceNumberType
    ACCESS  read-only
    STATUS  mandatory
    DESCRIPTION
             ""
    ::= { daxConnectionEntry 40 }


  daxNewMapTypeFrom OBJECT-TYPE
    SYNTAX  INTEGER {
      none(0),
      t1-e1(1),
      iDSL(2),
      gsdsl(4),
      toH110(5)
      }
    ACCESS  read-write
    STATUS  mandatory
    DESCRIPTION
             ""
    ::= { daxConnectionEntry 41 }

  daxNewMapNumberFrom OBJECT-TYPE
    SYNTAX  GSDSLDaxDeviceStreamType
    ACCESS  read-only
    STATUS  mandatory
    DESCRIPTION
             ""
    ::= { daxConnectionEntry 42 }

  daxNewMapTypeH110 OBJECT-TYPE
    SYNTAX  INTEGER {
      none(0),
      fromH110(6)
      }
    ACCESS  read-only
    STATUS  mandatory
    DESCRIPTION
             ""
    ::= { daxConnectionEntry 43 }


  daxNewMapNumberH110 OBJECT-TYPE
    SYNTAX  GSDSLDaxDeviceStreamType
    ACCESS  read-only
    STATUS  mandatory
    DESCRIPTION
             ""
    ::= { daxConnectionEntry 44 }

  daxNewMapSlotH110    OBJECT-TYPE
    SYNTAX  OCTET STRING (SIZE (0..40))
    ACCESS  read-only
    STATUS  mandatory
    DESCRIPTION
             "This variable is used to specify the range of slots to be used 
              in the connection. The following notation will be used
              1) a dash  (-) will be used to specify a range of slots i.e. 5 - 7
              2) a comma (,) will be used to specify non-contiguous slots 5,8,15
              to speficy slots 1,2,3,4,7,15,16, and 17 use the following notation
              1-4,7,15 - 17
              NOTE: The total number of slots specified here must match the total 
              number of slots specified in the daxDeviceSlotFrom variable"
    ::= { daxConnectionEntry 45 }

  daxM6511DeviceNumberToT1E1 OBJECT-TYPE
    SYNTAX  T1E1DaxM6511DeviceNumberType
    ACCESS  read-write
    STATUS  mandatory
    DESCRIPTION
             "After selecting the device type, this number will determine which device 
              in the bank will be used."
    ::= { daxConnectionEntry 46 }

  daxM6511DeviceNumberFromT1E1 OBJECT-TYPE
    SYNTAX  T1E1DaxM6511DeviceNumberType
    ACCESS  read-write
    STATUS  mandatory
    DESCRIPTION
             "After selecting the device type, this number will determine which device 
              in the bank will be used."
    ::= { daxConnectionEntry 47 }

  daxM6511Tug3Number OBJECT-TYPE
    SYNTAX  INTEGER {
      tug3-1(1),
      tug3-2(2),
      tug3-3(3)
      }
    ACCESS  read-write
    STATUS  mandatory
    DESCRIPTION
             " "
    ::= { daxConnectionEntry 48 }

  daxM6511Au3Number OBJECT-TYPE
    SYNTAX  INTEGER {
      au3-1(1),
      au3-2(2),
      au3-3(3)
      }
    ACCESS  read-write
    STATUS  mandatory
    DESCRIPTION
             " "
    ::= { daxConnectionEntry 49 }

  daxM6511Tug2Number OBJECT-TYPE
    SYNTAX  INTEGER {
      tug2-1(1),
      tug2-2(2),
      tug2-3(3),
      tug2-4(4),
      tug2-5(5),
      tug2-6(6),
      tug2-7(7)
      }
    ACCESS  read-write
    STATUS  mandatory
    DESCRIPTION
             " "
    ::= { daxConnectionEntry 50 }

  daxM6511Tu12Number OBJECT-TYPE
    SYNTAX  INTEGER {
      tu12-1(1),
      tu12-2(2),
      tu12-3(3)
      }
    ACCESS  read-write
    STATUS  mandatory
    DESCRIPTION
             " "
    ::= { daxConnectionEntry 51 }

  --*************************************************************************
  --*************************************************************************
  --                                 WAN Connection Table
  -- This read only table shows the current connections in reference to the
  -- WAN ports
  --*************************************************************************
  --*************************************************************************
  daxWANConnectionTable OBJECT-TYPE
    SYNTAX  SEQUENCE OF DaxWANConnectionEntry
    ACCESS  not-accessible
    STATUS  mandatory
    DESCRIPTION
	          ""
    ::= { dax 3 }

  daxWANConnectionEntry OBJECT-TYPE
    SYNTAX  DaxWANConnectionEntry
    ACCESS  not-accessible
    STATUS  mandatory
    DESCRIPTION
            "A single entry in the table designating a connection 
             from a single interface o another interface"
    INDEX   { daxWANConnectionID }
    ::= { daxWANConnectionTable 1 }

  DaxWANConnectionEntry ::=
    SEQUENCE {
      daxWANConnectionID          Index,
      daxWAN0DeviceType           INTEGER,
      daxWAN0DeviceNumber         DaxDeviceNumberType,
      daxWAN0DeviceSlot           INTEGER,

      daxWAN1DeviceType           INTEGER,
      daxWAN1DeviceNumber         DaxDeviceNumberType,
      daxWAN1DeviceSlot           INTEGER,

      daxWAN2DeviceType           INTEGER,
      daxWAN2DeviceNumber         DaxDeviceNumberType,
      daxWAN2DeviceSlot           INTEGER,

      daxWAN3DeviceType           INTEGER,
      daxWAN3DeviceNumber         DaxDeviceNumberType,
      daxWAN3DeviceSlot           INTEGER,

      daxWAN4DeviceType           INTEGER,
      daxWAN4DeviceNumber         DaxDeviceNumberType,
      daxWAN4DeviceSlot           INTEGER,

      daxWAN5DeviceType           INTEGER,
      daxWAN5DeviceNumber         DaxDeviceNumberType,
      daxWAN5DeviceSlot           INTEGER,

      daxWAN6DeviceType           INTEGER,
      daxWAN6DeviceNumber         DaxDeviceNumberType,
      daxWAN6DeviceSlot           INTEGER,

      daxWAN7DeviceType           INTEGER,
      daxWAN7DeviceNumber         DaxDeviceNumberType,
      daxWAN7DeviceSlot           INTEGER,

      daxWAN8DeviceType           INTEGER,
      daxWAN8DeviceNumber         DaxDeviceNumberType,
      daxWAN8DeviceSlot           INTEGER,

      daxWAN9DeviceType           INTEGER,
      daxWAN9DeviceNumber         DaxDeviceNumberType,
      daxWAN9DeviceSlot           INTEGER,

      daxWAN10DeviceType           INTEGER,
      daxWAN10DeviceNumber         DaxDeviceNumberType,
      daxWAN10DeviceSlot           INTEGER,

      daxWAN11DeviceType           INTEGER,
      daxWAN11DeviceNumber         DaxDeviceNumberType,
      daxWAN11DeviceSlot           INTEGER,

      daxWAN12DeviceType           INTEGER,
      daxWAN12DeviceNumber         DaxDeviceNumberType,
      daxWAN12DeviceSlot           INTEGER,

      daxWAN13DeviceType           INTEGER,
      daxWAN13DeviceNumber         DaxDeviceNumberType,
      daxWAN13DeviceSlot           INTEGER,

      daxWAN14DeviceType           INTEGER,
      daxWAN14DeviceNumber         DaxDeviceNumberType,
      daxWAN14DeviceSlot           INTEGER,

      daxWAN15DeviceType           INTEGER,
      daxWAN15DeviceNumber         DaxDeviceNumberType,
      daxWAN15DeviceSlot           INTEGER

      }

  daxWANConnectionID OBJECT-TYPE
    SYNTAX  Index
    ACCESS  read-only
    STATUS  mandatory
    DESCRIPTION
             "An index into the WAN connection table."
    ::= { daxWANConnectionEntry 1 }


  daxWAN0DeviceType OBJECT-TYPE
    SYNTAX  INTEGER {
      open(0),
      t1-e1(1),
      iDSL(2),
      mDSL(3)
      }
    ACCESS  read-only
    STATUS  mandatory
    DESCRIPTION
             ""
    ::= { daxWANConnectionEntry 2 }

  daxWAN0DeviceNumber OBJECT-TYPE
    SYNTAX  DaxDeviceNumberType
    ACCESS  read-only
    STATUS  mandatory
    DESCRIPTION
             ""
    ::= { daxWANConnectionEntry 3 }

  daxWAN0DeviceSlot OBJECT-TYPE
    SYNTAX  INTEGER
    ACCESS  read-only
    STATUS  mandatory
    DESCRIPTION
             ""
    ::= { daxWANConnectionEntry 4 }
  --*************************************************************************
  daxWAN1DeviceType OBJECT-TYPE
    SYNTAX  INTEGER {
      open(0),
      t1-e1(1),
      iDSL(2),
      mDSL(3)
      }
    ACCESS  read-only
    STATUS  mandatory
    DESCRIPTION
             ""
    ::= { daxWANConnectionEntry 5 }

  daxWAN1DeviceNumber OBJECT-TYPE
    SYNTAX  DaxDeviceNumberType
    ACCESS  read-only
    STATUS  mandatory
    DESCRIPTION
             ""
    ::= { daxWANConnectionEntry 6 }

  daxWAN1DeviceSlot OBJECT-TYPE
    SYNTAX  INTEGER
    ACCESS  read-only
    STATUS  mandatory
    DESCRIPTION
             ""
    ::= { daxWANConnectionEntry 7 }

  --*************************************************************************
  daxWAN2DeviceType OBJECT-TYPE
    SYNTAX  INTEGER {
      open(0),
      t1-e1(1),
      iDSL(2),
      mDSL(3)
      }
    ACCESS  read-only
    STATUS  mandatory
    DESCRIPTION
             ""
    ::= { daxWANConnectionEntry 8 }

  daxWAN2DeviceNumber OBJECT-TYPE
    SYNTAX  DaxDeviceNumberType
    ACCESS  read-only
    STATUS  mandatory
    DESCRIPTION
             ""
    ::= { daxWANConnectionEntry 9 }

  daxWAN2DeviceSlot OBJECT-TYPE
    SYNTAX  INTEGER
    ACCESS  read-only
    STATUS  mandatory
    DESCRIPTION
             ""
    ::= { daxWANConnectionEntry 10 }

  --*************************************************************************
  daxWAN3DeviceType OBJECT-TYPE
    SYNTAX  INTEGER {
      open(0),
      t1-e1(1),
      iDSL(2),
      mDSL(3)
      }
    ACCESS  read-only
    STATUS  mandatory
    DESCRIPTION
             ""
    ::= { daxWANConnectionEntry 11 }

  daxWAN3DeviceNumber OBJECT-TYPE
    SYNTAX  DaxDeviceNumberType
    ACCESS  read-only
    STATUS  mandatory
    DESCRIPTION
             ""
    ::= { daxWANConnectionEntry 12 }

  daxWAN3DeviceSlot OBJECT-TYPE
    SYNTAX  INTEGER
    ACCESS  read-only
    STATUS  mandatory
    DESCRIPTION
             ""
    ::= { daxWANConnectionEntry 13 }

  daxWAN4DeviceType OBJECT-TYPE
    SYNTAX  INTEGER {
      open(0),
      t1-e1(1),
      iDSL(2),
      mDSL(3)
      }
    ACCESS  read-only
    STATUS  mandatory
    DESCRIPTION
             ""
    ::= { daxWANConnectionEntry 14 }

  daxWAN4DeviceNumber OBJECT-TYPE
    SYNTAX  DaxDeviceNumberType
    ACCESS  read-only
    STATUS  mandatory
    DESCRIPTION
             ""
    ::= { daxWANConnectionEntry 15 }

  daxWAN4DeviceSlot OBJECT-TYPE
    SYNTAX  INTEGER
    ACCESS  read-only
    STATUS  mandatory
    DESCRIPTION
             ""
    ::= { daxWANConnectionEntry 16 }

  daxWAN5DeviceType OBJECT-TYPE
    SYNTAX  INTEGER {
      open(0),
      t1-e1(1),
      iDSL(2),
      mDSL(3)
      }
    ACCESS  read-only
    STATUS  mandatory
    DESCRIPTION
             ""
    ::= { daxWANConnectionEntry 17 }

  daxWAN5DeviceNumber OBJECT-TYPE
    SYNTAX  DaxDeviceNumberType
    ACCESS  read-only
    STATUS  mandatory
    DESCRIPTION
             ""
    ::= { daxWANConnectionEntry 18 }

  daxWAN5DeviceSlot OBJECT-TYPE
    SYNTAX  INTEGER
    ACCESS  read-only
    STATUS  mandatory
    DESCRIPTION
             ""
    ::= { daxWANConnectionEntry 19 }

  daxWAN6DeviceType OBJECT-TYPE
    SYNTAX  INTEGER {
      open(0),
      t1-e1(1),
      iDSL(2),
      mDSL(3)
      }
    ACCESS  read-only
    STATUS  mandatory
    DESCRIPTION
             ""
    ::= { daxWANConnectionEntry 20 }

  daxWAN6DeviceNumber OBJECT-TYPE
    SYNTAX  DaxDeviceNumberType
    ACCESS  read-only
    STATUS  mandatory
    DESCRIPTION
             ""
    ::= { daxWANConnectionEntry 21 }

  daxWAN6DeviceSlot OBJECT-TYPE
    SYNTAX  INTEGER
    ACCESS  read-only
    STATUS  mandatory
    DESCRIPTION
             ""
    ::= { daxWANConnectionEntry 22 }

  daxWAN7DeviceType OBJECT-TYPE
    SYNTAX  INTEGER {
      open(0),
      t1-e1(1),
      iDSL(2),
      mDSL(3)
      }
    ACCESS  read-only
    STATUS  mandatory
    DESCRIPTION
             ""
    ::= { daxWANConnectionEntry 23 }

  daxWAN7DeviceNumber OBJECT-TYPE
    SYNTAX  DaxDeviceNumberType
    ACCESS  read-only
    STATUS  mandatory
    DESCRIPTION
             ""
    ::= { daxWANConnectionEntry 24 }

  daxWAN7DeviceSlot OBJECT-TYPE
    SYNTAX  INTEGER
    ACCESS  read-only
    STATUS  mandatory
    DESCRIPTION
             ""
    ::= { daxWANConnectionEntry 25 }


  daxWAN8DeviceType OBJECT-TYPE
    SYNTAX  INTEGER {
      open(0),
      t1-e1(1),
      iDSL(2),
      mDSL(3)
      }
    ACCESS  read-only
    STATUS  mandatory
    DESCRIPTION
             ""
    ::= { daxWANConnectionEntry 26 }

  daxWAN8DeviceNumber OBJECT-TYPE
    SYNTAX  DaxDeviceNumberType
    ACCESS  read-only
    STATUS  mandatory
    DESCRIPTION
             ""
    ::= { daxWANConnectionEntry 27 }

  daxWAN8DeviceSlot OBJECT-TYPE
    SYNTAX  INTEGER
    ACCESS  read-only
    STATUS  mandatory
    DESCRIPTION
             ""
    ::= { daxWANConnectionEntry 28 }

  daxWAN9DeviceType OBJECT-TYPE
    SYNTAX  INTEGER {
      open(0),
      t1-e1(1),
      iDSL(2),
      mDSL(3)
      }
    ACCESS  read-only
    STATUS  mandatory
    DESCRIPTION
             ""
    ::= { daxWANConnectionEntry 29 }

  daxWAN9DeviceNumber OBJECT-TYPE
    SYNTAX  DaxDeviceNumberType
    ACCESS  read-only
    STATUS  mandatory
    DESCRIPTION
             ""
    ::= { daxWANConnectionEntry 30 }

  daxWAN9DeviceSlot OBJECT-TYPE
    SYNTAX  INTEGER
    ACCESS  read-only
    STATUS  mandatory
    DESCRIPTION
             ""
    ::= { daxWANConnectionEntry 31 }

  daxWAN10DeviceType OBJECT-TYPE
    SYNTAX  INTEGER {
      open(0),
      t1-e1(1),
      iDSL(2),
      mDSL(3)
      }
    ACCESS  read-only
    STATUS  mandatory
    DESCRIPTION
             ""
    ::= { daxWANConnectionEntry 32 }

  daxWAN10DeviceNumber OBJECT-TYPE
    SYNTAX  DaxDeviceNumberType
    ACCESS  read-only
    STATUS  mandatory
    DESCRIPTION
             ""
    ::= { daxWANConnectionEntry 33 }

  daxWAN10DeviceSlot OBJECT-TYPE
    SYNTAX  INTEGER
    ACCESS  read-only
    STATUS  mandatory
    DESCRIPTION
             ""
    ::= { daxWANConnectionEntry 34 }

  daxWAN11DeviceType OBJECT-TYPE
    SYNTAX  INTEGER {
      open(0),
      t1-e1(1),
      iDSL(2),
      mDSL(3)
      }
    ACCESS  read-only
    STATUS  mandatory
    DESCRIPTION
             ""
    ::= { daxWANConnectionEntry 35 }

  daxWAN11DeviceNumber OBJECT-TYPE
    SYNTAX  DaxDeviceNumberType
    ACCESS  read-only
    STATUS  mandatory
    DESCRIPTION
             ""
    ::= { daxWANConnectionEntry 36 }

  daxWAN11DeviceSlot OBJECT-TYPE
    SYNTAX  INTEGER
    ACCESS  read-only
    STATUS  mandatory
    DESCRIPTION
             ""
    ::= { daxWANConnectionEntry 37 }

  daxWAN12DeviceType OBJECT-TYPE
    SYNTAX  INTEGER {
      open(0),
      t1-e1(1),
      iDSL(2),
      mDSL(3)
      }
    ACCESS  read-only
    STATUS  mandatory
    DESCRIPTION
             ""
    ::= { daxWANConnectionEntry 38 }

  daxWAN12DeviceNumber OBJECT-TYPE
    SYNTAX  DaxDeviceNumberType
    ACCESS  read-only
    STATUS  mandatory
    DESCRIPTION
             ""
    ::= { daxWANConnectionEntry 39 }

  daxWAN12DeviceSlot OBJECT-TYPE
    SYNTAX  INTEGER
    ACCESS  read-only
    STATUS  mandatory
    DESCRIPTION
             ""
    ::= { daxWANConnectionEntry 40 }

  daxWAN13DeviceType OBJECT-TYPE
    SYNTAX  INTEGER {
      open(0),
      t1-e1(1),
      iDSL(2),
      mDSL(3)
      }
    ACCESS  read-only
    STATUS  mandatory
    DESCRIPTION
             ""
    ::= { daxWANConnectionEntry 41 }

  daxWAN13DeviceNumber OBJECT-TYPE
    SYNTAX  DaxDeviceNumberType
    ACCESS  read-only
    STATUS  mandatory
    DESCRIPTION
             ""
    ::= { daxWANConnectionEntry 42 }

  daxWAN13DeviceSlot OBJECT-TYPE
    SYNTAX  INTEGER
    ACCESS  read-only
    STATUS  mandatory
    DESCRIPTION
             ""
    ::= { daxWANConnectionEntry 43 }

  daxWAN14DeviceType OBJECT-TYPE
    SYNTAX  INTEGER {
      open(0),
      t1-e1(1),
      iDSL(2),
      mDSL(3)
      }
    ACCESS  read-only
    STATUS  mandatory
    DESCRIPTION
             ""
    ::= { daxWANConnectionEntry 44 }

  daxWAN14DeviceNumber OBJECT-TYPE
    SYNTAX  DaxDeviceNumberType
    ACCESS  read-only
    STATUS  mandatory
    DESCRIPTION
             ""
    ::= { daxWANConnectionEntry 45 }

  daxWAN14DeviceSlot OBJECT-TYPE
    SYNTAX  INTEGER
    ACCESS  read-only
    STATUS  mandatory
    DESCRIPTION
             ""
    ::= { daxWANConnectionEntry 46 }

  daxWAN15DeviceType OBJECT-TYPE
    SYNTAX  INTEGER {
      open(0),
      t1-e1(1),
      iDSL(2),
      mDSL(3)
      }
    ACCESS  read-only
    STATUS  mandatory
    DESCRIPTION
             ""
    ::= { daxWANConnectionEntry 47 }

  daxWAN15DeviceNumber OBJECT-TYPE
    SYNTAX  DaxDeviceNumberType
    ACCESS  read-only
    STATUS  mandatory
    DESCRIPTION
             ""
    ::= { daxWANConnectionEntry 48 }

  daxWAN15DeviceSlot OBJECT-TYPE
    SYNTAX  INTEGER
    ACCESS  read-only
    STATUS  mandatory
    DESCRIPTION
             ""
    ::= { daxWANConnectionEntry 49 }


  --*************************************************************************
  --*************************************************************************
  --                                 iDSL Connection Table
  -- This read only table shows the current connections in reference to the
  -- iDSL ports
  --*************************************************************************
  --*************************************************************************
  daxIDSLConnectionTable OBJECT-TYPE
    SYNTAX  SEQUENCE OF DaxIDSLConnectionEntry
    ACCESS  not-accessible
    STATUS  mandatory
    DESCRIPTION
	          ""
    ::= { dax 4 }

  daxIDSLConnectionEntry OBJECT-TYPE
    SYNTAX  DaxIDSLConnectionEntry
    ACCESS  not-accessible
    STATUS  mandatory
    DESCRIPTION
            "A single entry in the table designating a connection 
             from a single interface to another interface"
    INDEX   { daxIDSLConnectionID }
    ::= { daxIDSLConnectionTable 1 }

  DaxIDSLConnectionEntry ::=
    SEQUENCE {
      daxIDSLConnectionID         Index,

      daxIDSL1DeviceType           INTEGER,
      daxIDSL1DeviceNumber         DaxDeviceNumberType,
      daxIDSL1DeviceSlot           INTEGER,

      daxIDSL2DeviceType           INTEGER,
      daxIDSL2DeviceNumber         DaxDeviceNumberType,
      daxIDSL2DeviceSlot           INTEGER
      }

  daxIDSLConnectionID OBJECT-TYPE
    SYNTAX  Index
    ACCESS  read-only
    STATUS  mandatory
    DESCRIPTION
             "An index into the WAN connection table."
    ::= { daxIDSLConnectionEntry 1 }


  daxIDSL1DeviceType OBJECT-TYPE
    SYNTAX  INTEGER {
      open(0),
      t1-e1(1),
      iDSL(2)
      }
    ACCESS  read-only
    STATUS  mandatory
    DESCRIPTION
             "Time Slot 1 Connection information"
    ::= { daxIDSLConnectionEntry 2 }

  daxIDSL1DeviceNumber OBJECT-TYPE
    SYNTAX  DaxDeviceNumberType
    ACCESS  read-only
    STATUS  mandatory
    DESCRIPTION
             "Time Slot 1 Connection information"
    ::= { daxIDSLConnectionEntry 3 }

  daxIDSL1DeviceSlot OBJECT-TYPE
    SYNTAX  INTEGER
    ACCESS  read-only
    STATUS  mandatory
    DESCRIPTION
             "Time Slot 1 Connection information"
    ::= { daxIDSLConnectionEntry 4 }


  daxIDSL2DeviceType OBJECT-TYPE
    SYNTAX  INTEGER {
      open(0),
      t1-e1(1),
      iDSL(2)
      }
    ACCESS  read-only
    STATUS  mandatory
    DESCRIPTION
             "Time Slot 1 Connection information"
    ::= { daxIDSLConnectionEntry 5 }

  daxIDSL2DeviceNumber OBJECT-TYPE
    SYNTAX  DaxDeviceNumberType
    ACCESS  read-only
    STATUS  mandatory
    DESCRIPTION
             "Time Slot 1 Connection information"
    ::= { daxIDSLConnectionEntry 6 }

  daxIDSL2DeviceSlot OBJECT-TYPE
    SYNTAX  INTEGER
    ACCESS  read-only
    STATUS  mandatory
    DESCRIPTION
             "Time Slot 1 Connection information"
    ::= { daxIDSLConnectionEntry 7 }

  daxErrorReport OBJECT-TYPE
    SYNTAX  DisplayString
    ACCESS  read-only
    STATUS  mandatory
    DESCRIPTION "This read only string will show the reason that the last 
                 submission to the dax connection table was rejected. This
                 string will remain until either another error connection
                 is submitted or until a valid connection is submitted."
    ::= { dax 5 }


  daxCliConnection OBJECT-TYPE
    SYNTAX  DisplayString
    ACCESS  read-write
    STATUS  mandatory
    DESCRIPTION "This variable allows the user to input a static connection into the box. 
                 Use the following convention for adding new connections:
                 DeviceA:PortA:SlotsA:DeviceB:PortB:SlotsB

                 Device Options - The interface that you would like to select
                   1) t1-e1
                   2) iDSL
                 Port Options - The Port Number (starting at 1) that you would like to configure
                 Slots - The slots that you would like to use. The following notations are allowed
                   1) dash:  (-) 1 - 4
                   2) comma: (,) 1,4,9
                   3) combo: 1 - 2, 3,6 - 7

                 Example: To connect T1 Port 1, timeslots 1 and 2 to iDSL Port 3, timeslots 1,2 input the following
                 t1-e1:1:1 - 2,iDSL:3:1 - 2"
    ::= { dax 6 }

  sysdaxClockMainRef OBJECT-TYPE
    SYNTAX  MDSLDaxReferenceType
    ACCESS  read-write
    STATUS  mandatory
    DESCRIPTION
             "Master: This defines the clock source from which the system
              will base its timing.  Secondary: This defines the clock source
              from which the system will base its timing in the event of
              a complete failure of the master.  Slave: This defines the 
              clock source which will be driven to the NETREF #1."
    ::= { dax 7 }

  sysdaxClockFallbackRef OBJECT-TYPE
    SYNTAX  MDSLDaxReferenceType
    ACCESS  read-write
    STATUS  mandatory
    DESCRIPTION
             "Master: This defines the clock source from which the system
              will base its timing if the MainRef goes bad.  Secondary: not used.
              Slave: This defines the clock source which will be driven to
              the NETREF #2."
    ::= { dax 8 }

  sysdaxClockFailure OBJECT-TYPE
    SYNTAX  INTEGER {
      no-failures(0),
      main-ref-fail(1),
      fallback-ref-fail(2),
      master-system-clock-fail(4),
      secondary-system-clock-fail(8)
      }
    ACCESS  read-only
    STATUS  mandatory
    DESCRIPTION
             "Identifies which clock this circuit has detected as failed. A
              clock is failed if transissions are not seen, or if the
              number of clocks per frame period is not correct.  In some
              cases the failure is actually a detection of LOS on the WAN
              interface used for the reference.  This is bit enumerated."
    ::= { dax 9 }


  sysGSdslClockMainRef OBJECT-TYPE
    SYNTAX  GSDSLDaxReferenceType
    ACCESS  read-write
    STATUS  mandatory
    DESCRIPTION
             "Master: This defines the clock source from which the system
              will base its timing.  Secondary: This defines the clock source
              from which the system will base its timing in the event of
              a complete failure of the master.  Slave: This defines the 
              clock source which will be driven to the NETREF #1."
    ::= { dax 10 }

  sysGSdslClockFallbackRef OBJECT-TYPE
    SYNTAX  GSDSLDaxReferenceType
    ACCESS  read-write
    STATUS  mandatory
    DESCRIPTION
             "Master: This defines the clock source from which the system
              will base its timing if the MainRef goes bad.  Secondary: not used.
              Slave: This defines the clock source which will be driven to
              the NETREF #2."
    ::= { dax 11 }


  sysGSClockMode OBJECT-TYPE
    SYNTAX  INTEGER {
      master(1),
      secondary(2),
      slave(3)
      }
    ACCESS  read-write
    STATUS  mandatory
    DESCRIPTION
             "Designated this circuits roll in the overall clocking
              scheme of the entire system.  The master devide is
              responsible for providing the system clock in synchronization
              with one of his references.  The secondary does this same job
              in the absense of the master.  The slaves simply listen to
              the system clock, but may provide a reference for use by
              the master."
    ::= { dax 12 }



  daxFallbackTable OBJECT-TYPE
    SYNTAX  SEQUENCE OF DaxFallbackEntry
    ACCESS  not-accessible
    STATUS  mandatory
    DESCRIPTION
	          ""
    ::= { dax 13 }

  daxFallbackEntry OBJECT-TYPE
    SYNTAX  DaxFallbackEntry
    ACCESS  not-accessible
    STATUS  mandatory
    DESCRIPTION
            ""
    INDEX   { daxFallbackID }
    ::= { daxFallbackTable 1 }

  DaxFallbackEntry ::=
    SEQUENCE {
      daxFallbackID                 Index,
                                    
      daxWatchPort                  T1E1DaxDeviceNumberType,
      daxWatchSlot                  OCTET STRING,
                                    
      daxFallbackPort               T1E1DaxDeviceNumberType,
      daxFallbackSlot               OCTET STRING,

      daxFallbackConnectionStatus   INTEGER,
      daxFallbackRecovery           INTEGER,

      daxWatchTypeGsDSL             INTEGER,
      daxWatchPortGsDSL             GSDSLDaxDeviceNumberType,

      daxFallbackTypeGsDSL          INTEGER,
      daxFallbackPortGsDSL          GSDSLDaxDeviceStreamType,

      daxFallbackTypeGsDSLH110      INTEGER,
      daxFallbackPortGsDSLH110      GSDSLDaxDeviceStreamType,
      daxFallbackSlotH110           OCTET STRING,

      daxFallbackTypeiDSL           INTEGER,
      daxWatchTypeiDSL              INTEGER
      }

  daxFallbackID OBJECT-TYPE
    SYNTAX  Index
    ACCESS  read-write
    STATUS  mandatory
    DESCRIPTION
             "An index into the connection table."
    ::= { daxFallbackEntry 1 }


  daxWatchPort OBJECT-TYPE
    SYNTAX  T1E1DaxDeviceNumberType
    ACCESS  read-write
    STATUS  mandatory
    DESCRIPTION
             "Specifies the T1/E1 port to watch for fallbacks"
    ::= { daxFallbackEntry 2 }

  daxWatchSlot          OBJECT-TYPE
    SYNTAX  OCTET STRING (SIZE (0..40))
    ACCESS  read-write
    STATUS  mandatory
    DESCRIPTION
             "This variable is used to specify the range of slots to be used 
              in the fallback. The following notation will be used
              1) a dash  (-) will be used to specify a range of slots i.e. 5 - 7
              2) a comma (,) will be used to specify non-contiguous slots 5,8,15
              to speficy slots 1,2,3,4,7,15,16, and 17 use the following notation
              1-4,7,15 - 17. 
              NOTE: This must match one of the connection entries already supplied
              to the system."
    ::= { daxFallbackEntry 3 }


  daxFallbackPort OBJECT-TYPE
    SYNTAX  T1E1DaxDeviceNumberType
    ACCESS  read-write
    STATUS  mandatory
    DESCRIPTION
             "After selecting the device type, this number will determine which device 
              in the bank will be used."
    ::= { daxFallbackEntry 4 }

  daxFallbackSlot      OBJECT-TYPE
    SYNTAX  OCTET STRING (SIZE (0..40))
    ACCESS  read-write
    STATUS  mandatory
    DESCRIPTION
             "This variable is used to specify the range of slots to be used 
              in the fallback. The following notation will be used
              1) a dash  (-) will be used to specify a range of slots i.e. 5 - 7
              2) a comma (,) will be used to specify non-contiguous slots 5,8,15
              to speficy slots 1,2,3,4,7,15,16, and 17 use the following notation
              1-4,7,15 - 17. 
              NOTE: This is the slots that will be used if a fallback occurs"
    ::= { daxFallbackEntry 5 }

  daxFallbackConnectionStatus OBJECT-TYPE
    SYNTAX  INTEGER {
      active(0),
      delete(1)
      }
    ACCESS  read-write
    STATUS  mandatory
    DESCRIPTION
             ""
    ::= { daxFallbackEntry 6 }

  daxFallbackRecovery OBJECT-TYPE
    SYNTAX  INTEGER {
      userForceRecovery(0),
      autoRecovery(1)
      }
    ACCESS  read-write
    STATUS  mandatory
    DESCRIPTION
             ""
    ::= { daxFallbackEntry 7 }


  daxWatchTypeGsDSL OBJECT-TYPE
    SYNTAX  INTEGER {
      none(0),
      t1-e1(1),
      gsdsl(4)
      }
    ACCESS  read-write
    STATUS  mandatory
    DESCRIPTION
             ""
    ::= { daxFallbackEntry 8 }


  daxWatchPortGsDSL OBJECT-TYPE
    SYNTAX  GSDSLDaxDeviceNumberType
    ACCESS  read-write
    STATUS  mandatory
    DESCRIPTION
             ""
    ::= { daxFallbackEntry 9 }

  daxFallbackTypeGsDSL OBJECT-TYPE
    SYNTAX  INTEGER {
      none(0),
      t1-e1(1),
      gsdsl(4),
      toH110(5)
      }
    ACCESS  read-write
    STATUS  mandatory
    DESCRIPTION
             ""
    ::= { daxFallbackEntry 10 }

  daxFallbackPortGsDSL OBJECT-TYPE
    SYNTAX  GSDSLDaxDeviceStreamType
    ACCESS  read-write
    STATUS  mandatory
    DESCRIPTION
             ""
    ::= { daxFallbackEntry 11 }

  daxFallbackTypeGsDSLH110 OBJECT-TYPE
    SYNTAX  INTEGER {
      none(0),
      fromH110(6)
      }
    ACCESS  read-write
    STATUS  mandatory
    DESCRIPTION
             ""
    ::= { daxFallbackEntry 12 }

  daxFallbackPortGsDSLH110 OBJECT-TYPE
    SYNTAX  GSDSLDaxDeviceStreamType
    ACCESS  read-write
    STATUS  mandatory
    DESCRIPTION
             ""
    ::= { daxFallbackEntry 13 }

  daxFallbackSlotH110      OBJECT-TYPE
    SYNTAX  OCTET STRING (SIZE (0..40))
    ACCESS  read-write
    STATUS  mandatory
    DESCRIPTION
             "This variable is used to specify the range of slots to be used 
              in the fallback. The following notation will be used
              1) a dash  (-) will be used to specify a range of slots i.e. 5 - 7
              2) a comma (,) will be used to specify non-contiguous slots 5,8,15
              to speficy slots 1,2,3,4,7,15,16, and 17 use the following notation
              1-4,7,15 - 17. 
              NOTE: This is the slots that will be used if a fallback occurs"
    ::= { daxFallbackEntry 14 }

  daxWatchTypeiDSL OBJECT-TYPE
    SYNTAX  INTEGER {
      none(0),
      t1-e1(1),
      iDSL(2)
      }
    ACCESS  read-write
    STATUS  mandatory
    DESCRIPTION
             ""
    ::= { daxFallbackEntry 15 }

  daxFallbackTypeiDSL OBJECT-TYPE
    SYNTAX  INTEGER {
      none(0),
      t1-e1(1),
      iDSL(2),
      toH110(5)
      }
    ACCESS  read-write
    STATUS  mandatory
    DESCRIPTION
             ""
    ::= { daxFallbackEntry 16 }


  --*************************************************************************
  --*************************************************************************
  --                       cPCI Clock Management Functions
  --*************************************************************************
  --*************************************************************************
-- error and status registers
  daxClockFallbackAction OBJECT-TYPE
    SYNTAX  INTEGER {
      forceFallback(1),
      returnFromFallback(2),
      clearErrors(3)
      }
    ACCESS  read-write
    STATUS  mandatory
    DESCRIPTION
             ""
    ::= { dax 14 }

-- dynamic error information - 
  daxDynamicClkErrCtC8B OBJECT-TYPE
    SYNTAX  INTEGER {
      noError(0),
      errorState(1)
      }
    ACCESS  read-only
    STATUS  mandatory
    DESCRIPTION
             ""
    ::= { dax 15 }

  daxDynamicClkErrCtC8A OBJECT-TYPE
    SYNTAX  INTEGER {
      noError(0),
      errorState(1)
      }
    ACCESS  read-only
    STATUS  mandatory
    DESCRIPTION
             ""
    ::= { dax 16 }

  daxDynamicClkErrApll1 OBJECT-TYPE
    SYNTAX  INTEGER {
      noError(0),
      errorState(1)
      }
    ACCESS  read-only
    STATUS  mandatory
    DESCRIPTION
             ""
    ::= { dax 17 }

  daxDynamicClkErrDpll1 OBJECT-TYPE
    SYNTAX  INTEGER {
      noError(0),
      errorState(1)
      }
    ACCESS  read-only
    STATUS  mandatory
    DESCRIPTION
             ""
    ::= { dax 18 }

  daxDynamicClkErrNet2 OBJECT-TYPE
    SYNTAX  INTEGER {
      noError(0),
      errorState(1)
      }
    ACCESS  read-only
    STATUS  mandatory
    DESCRIPTION
             ""
    ::= { dax 19 }

  daxDynamicClkErrNet1 OBJECT-TYPE
    SYNTAX  INTEGER {
      noError(0),
      errorState(1)
      }
    ACCESS  read-only
    STATUS  mandatory
    DESCRIPTION
             ""
    ::= { dax 20 }

  daxDynamicClkErrFrB OBJECT-TYPE
    SYNTAX  INTEGER {
      noError(0),
      errorState(1)
      }
    ACCESS  read-only
    STATUS  mandatory
    DESCRIPTION
             ""
    ::= { dax 21 }

  daxDynamicClkErrFrA OBJECT-TYPE
    SYNTAX  INTEGER {
      noError(0),
      errorState(1)
      }
    ACCESS  read-only
    STATUS  mandatory
    DESCRIPTION
             ""
    ::= { dax 22 }


 --*************************************************************************
  --*************************************************************************
  --                                 Added for 26xx
  --*************************************************************************
  --*************************************************************************

  sysdaxClockMainRefNoDSL OBJECT-TYPE
    SYNTAX  DaxReferenceTypeNoDSL
    ACCESS  read-write
    STATUS  mandatory
    DESCRIPTION
             "Master: This defines the clock source from which the system
              will base its timing.  Secondary: This defines the clock source
              from which the system will base its timing in the event of
              a complete failure of the master.  Slave: This defines the 
              clock source which will be driven to the NETREF #1."
    ::= { dax 23 }

  sysdaxClockFallbackRefNoDSL OBJECT-TYPE
    SYNTAX  DaxReferenceTypeNoDSL
    ACCESS  read-write
    STATUS  mandatory
    DESCRIPTION
             "Master: This defines the clock source from which the system
              will base its timing if the MainRef goes bad.  Secondary: not used.
              Slave: This defines the clock source which will be driven to
              the NETREF #2."
    ::= { dax 24 }


  daxFallbackIndicator OBJECT-TYPE
    SYNTAX  INTEGER {
      noFallback(0),
      fallbackState(1)
      }
    ACCESS  read-only
    STATUS  mandatory
    DESCRIPTION
             ""
    ::= { dax 50 }

  daxFallbackState OBJECT-TYPE
    SYNTAX  INTEGER {
      primary(0),
      to-Primary(1),
      secondary(2),
      to-Secondary(3),
      failSafe-1(4),
      failSafe-2(5),
      initial(7)
      }
    ACCESS  read-only
    STATUS  mandatory
    DESCRIPTION
             ""
    ::= { dax 51 }


--******
--******
-- dynamic error information - 
  daxFallbackTriggerCtC8B OBJECT-TYPE
    SYNTAX  INTEGER {
      disable(0),
      enable(1)
      }
    ACCESS  read-only
    STATUS  mandatory
    DESCRIPTION
             ""
    ::= { dax 60 }

  daxFallbackTriggerCtC8A OBJECT-TYPE
    SYNTAX  INTEGER {
      disable(0),
      enable(1)
      }
    ACCESS  read-only
    STATUS  mandatory
    DESCRIPTION
             ""
    ::= { dax 61 }

  daxFallbackTriggerApll1 OBJECT-TYPE
    SYNTAX  INTEGER {
      disable(0),
      enable(1)
      }
    ACCESS  read-only
    STATUS  mandatory
    DESCRIPTION
             ""
    ::= { dax 62 }

  daxFallbackTriggerDpll1 OBJECT-TYPE
    SYNTAX  INTEGER {
      disable(0),
      enable(1)
      }
    ACCESS  read-only
    STATUS  mandatory
    DESCRIPTION
             ""
    ::= { dax 63 }

  daxFallbackTriggerNet2 OBJECT-TYPE
    SYNTAX  INTEGER {
      disable(0),
      enable(1)
      }
    ACCESS  read-only
    STATUS  mandatory
    DESCRIPTION
             ""
    ::= { dax 64 }

  daxFallbackTriggerNet1 OBJECT-TYPE
    SYNTAX  INTEGER {
      disable(0),
      enable(1)
      }
    ACCESS  read-only
    STATUS  mandatory
    DESCRIPTION
             ""
    ::= { dax 65 }

  daxFallbackTriggerFrB OBJECT-TYPE
    SYNTAX  INTEGER {
      disable(0),
      enable(1)
      }
    ACCESS  read-only
    STATUS  mandatory
    DESCRIPTION
             ""
    ::= { dax 66 }

  daxFallbackTriggerFrA OBJECT-TYPE
    SYNTAX  INTEGER {
      disable(0),
      enable(1)
      }
    ACCESS  read-only
    STATUS  mandatory
    DESCRIPTION
             ""
    ::= { dax 67 }

--******
--******

--******
--******
-- dynamic error information - 
  daxWatchEnCtC8B OBJECT-TYPE
    SYNTAX  INTEGER {
      disable(0),
      enable(1)
      }
    ACCESS  read-only
    STATUS  mandatory
    DESCRIPTION
             ""
    ::= { dax 70 }

  daxWatchEnCtC8A OBJECT-TYPE
    SYNTAX  INTEGER {
      disable(0),
      enable(1)
      }
    ACCESS  read-only
    STATUS  mandatory
    DESCRIPTION
             ""
    ::= { dax 71 }

  daxWatchEnApll1 OBJECT-TYPE
    SYNTAX  INTEGER {
      disable(0),
      enable(1)
      }
    ACCESS  read-only
    STATUS  mandatory
    DESCRIPTION
             ""
    ::= { dax 72 }

  daxWatchEnDpll1 OBJECT-TYPE
    SYNTAX  INTEGER {
      disable(0),
      enable(1)
      }
    ACCESS  read-only
    STATUS  mandatory
    DESCRIPTION
             ""
    ::= { dax 73 }

  daxWatchEnNet2 OBJECT-TYPE
    SYNTAX  INTEGER {
      disable(0),
      enable(1)
      }
    ACCESS  read-only
    STATUS  mandatory
    DESCRIPTION
             ""
    ::= { dax 74 }

  daxWatchEnNet1 OBJECT-TYPE
    SYNTAX  INTEGER {
      disable(0),
      enable(1)
      }
    ACCESS  read-only
    STATUS  mandatory
    DESCRIPTION
             ""
    ::= { dax 75 }

  daxWatchEnFrB OBJECT-TYPE
    SYNTAX  INTEGER {
      disable(0),
      enable(1)
      }
    ACCESS  read-only
    STATUS  mandatory
    DESCRIPTION
             ""
    ::= { dax 76 }

  daxWatchEnFrA OBJECT-TYPE
    SYNTAX  INTEGER {
      disable(0),
      enable(1)
      }
    ACCESS  read-only
    STATUS  mandatory
    DESCRIPTION
             ""
    ::= { dax 77 }

--******
--******

--******
--******
-- dynamic error information - 
  daxLatchErrCtC8B OBJECT-TYPE
    SYNTAX  INTEGER {
      disable(0),
      enable(1)
      }
    ACCESS  read-only
    STATUS  mandatory
    DESCRIPTION
             ""
    ::= { dax 80 }

  daxLatchErrCtC8A OBJECT-TYPE
    SYNTAX  INTEGER {
      disable(0),
      enable(1)
      }
    ACCESS  read-only
    STATUS  mandatory
    DESCRIPTION
             ""
    ::= { dax 81 }

  daxLatchErrApll1 OBJECT-TYPE
    SYNTAX  INTEGER {
      disable(0),
      enable(1)
      }
    ACCESS  read-only
    STATUS  mandatory
    DESCRIPTION
             ""
    ::= { dax 82 }

  daxLatchErrDpll1 OBJECT-TYPE
    SYNTAX  INTEGER {
      disable(0),
      enable(1)
      }
    ACCESS  read-only
    STATUS  mandatory
    DESCRIPTION
             ""
    ::= { dax 83 }

  daxLatchErrNet2 OBJECT-TYPE
    SYNTAX  INTEGER {
      disable(0),
      enable(1)
      }
    ACCESS  read-only
    STATUS  mandatory
    DESCRIPTION
             ""
    ::= { dax 84 }

  daxLatchErrNet1 OBJECT-TYPE
    SYNTAX  INTEGER {
      disable(0),
      enable(1)
      }
    ACCESS  read-only
    STATUS  mandatory
    DESCRIPTION
             ""
    ::= { dax 85 }

  daxLatchErrFrB OBJECT-TYPE
    SYNTAX  INTEGER {
      disable(0),
      enable(1)
      }
    ACCESS  read-only
    STATUS  mandatory
    DESCRIPTION
             ""
    ::= { dax 86 }

  daxLatchErrFrA OBJECT-TYPE
    SYNTAX  INTEGER {
      disable(0),
      enable(1)
      }
    ACCESS  read-only
    STATUS  mandatory
    DESCRIPTION
             ""
    ::= { dax 87 }

--******
--******
  daxApll1Lock OBJECT-TYPE
    SYNTAX  INTEGER {
      inLock(0),
      outOfLock(1)
      }
    ACCESS  read-only
    STATUS  mandatory
    DESCRIPTION
             ""
    ::= { dax 90 }

  daxOutOfLockInd OBJECT-TYPE
    SYNTAX  INTEGER {
      inactive(0),
      active(1)
      }
    ACCESS  read-only
    STATUS  mandatory
    DESCRIPTION
             ""
    ::= { dax 91 }

  daxDpll1Lock OBJECT-TYPE
    SYNTAX  INTEGER {
      inLock(0),
      outOfLockSlow(1),
      outOfLockFast(2)
      }
    ACCESS  read-only
    STATUS  mandatory
    DESCRIPTION
             ""
    ::= { dax 92 }

  daxFailsafeIndicator OBJECT-TYPE
    SYNTAX  INTEGER {
      noError(0),
      failsafeActive(1)
      }
    ACCESS  read-only
    STATUS  mandatory
    DESCRIPTION
             ""
    ::= { dax 93 }


  daxFallbackInd OBJECT-TYPE
    SYNTAX  INTEGER {
      noError(0),
      fallbackActive(1)
      }
    ACCESS  read-only
    STATUS  mandatory
    DESCRIPTION
             ""
    ::= { dax 94 }

  daxFallbackType OBJECT-TYPE
    SYNTAX  INTEGER {
      fallbackDisabled(0),
      fixedSecondary(1),
      rotatingSecondary(2)
      }
    ACCESS  read-only
    STATUS  mandatory
    DESCRIPTION
             ""
    ::= { dax 100 }

  daxFallbackSetup OBJECT-TYPE
    SYNTAX  INTEGER {
      disabled(0),
      fallbackTriggers(8),
      fallbackTriggersEn(9)
      }
    ACCESS  read-only
    STATUS  mandatory
    DESCRIPTION
             ""
    ::= { dax 101 }

  daxActiveClockSet OBJECT-TYPE
    SYNTAX  INTEGER {
      y-active(0),
      x-active(1)
      }
    ACCESS  read-only
    STATUS  mandatory
    DESCRIPTION
             ""
    ::= { dax 102 }



  daxSystemTable OBJECT-TYPE
    SYNTAX  SEQUENCE OF DaxSystemEntry
    ACCESS  not-accessible
    STATUS  mandatory
    DESCRIPTION
	          ""
    ::= { dax 200 }

  daxSystemEntry OBJECT-TYPE
    SYNTAX  DaxSystemEntry
    ACCESS  not-accessible
    STATUS  mandatory
    DESCRIPTION
            ""
    INDEX   { daxSystemID }
    ::= { daxSystemTable 1 }

  DaxSystemEntry ::=
    SEQUENCE {
      daxSystemID                   Index,
      daxSystemType                 INTEGER,
      daxSystemTimeSlot             DisplayString,
      daxSystemRdWr                 INTEGER,
      daxSystemTag                  INTEGER,
      daxSystemStream               INTEGER
      }

  daxSystemID OBJECT-TYPE
    SYNTAX      Index
    ACCESS      read-only
    STATUS      mandatory
    DESCRIPTION ""
    ::= { daxSystemEntry 1 }

  daxSystemType OBJECT-TYPE
    SYNTAX  INTEGER {
      dslOutput(0),
      dslInput(1),
      h110(2)
      }
    ACCESS  read-only
    STATUS  mandatory
    DESCRIPTION
             ""
    ::= { daxSystemEntry 2 }

  daxSystemTimeSlot OBJECT-TYPE
    SYNTAX      DisplayString
    ACCESS      read-only
    STATUS      mandatory
    DESCRIPTION ""
    ::= { daxSystemEntry 3 }

      daxSystemRdWr OBJECT-TYPE
    SYNTAX  INTEGER {
      wr-Input(0),
      rd-Output(1)
      }
    ACCESS  read-only
    STATUS  mandatory
    DESCRIPTION
             ""
    ::= { daxSystemEntry 4 }

  daxSystemTag OBJECT-TYPE
    SYNTAX      INTEGER
    ACCESS      read-only
    STATUS      mandatory
    DESCRIPTION ""
    ::= { daxSystemEntry 5 }

  daxSystemStream OBJECT-TYPE
    SYNTAX      INTEGER
    ACCESS      read-only
    STATUS      mandatory
    DESCRIPTION ""
    ::= { daxSystemEntry 6 }


  daxConfigActiveMainInput OBJECT-TYPE
    SYNTAX  INTEGER {
      oscillator(0),
      netref1(17),
      netref2(18),
      lrefIndiv(33),
      lrefPaired(34),
      h110BusA(65),
      h110BusB(66),
      mc1R(68),
      mc1L(72),
      mvipC2(128),
      mvipC4(129),
      sc2M(132),
      sc4M(136)
      }
    ACCESS  read-only
    STATUS  mandatory
    DESCRIPTION
             ""
    ::= { dax 300 }

  daxConfigActiveMainDivider OBJECT-TYPE
    SYNTAX  INTEGER 
    ACCESS  read-only
    STATUS  mandatory
    DESCRIPTION
             ""
    ::= { dax 301 }

  daxConfigActiveAppl1Input OBJECT-TYPE
    SYNTAX  INTEGER {
      oscDiv4(0),
      mainDivOut(1),
      resourceDivOut(2),
      dpll1Out(4),
      priRefIn(8)
      }
    ACCESS  read-only
    STATUS  mandatory
    DESCRIPTION
             ""
    ::= { dax 302 }

  daxConfigActiveAppl1Rate OBJECT-TYPE
    SYNTAX  INTEGER {
      multBy16(0),
      multBy32(1)
      }
    ACCESS  read-only
    STATUS  mandatory
    DESCRIPTION
             ""
    ::= { dax 303 }

  daxConfigActiveMainInversion OBJECT-TYPE
    SYNTAX  INTEGER 
    ACCESS  read-only
    STATUS  mandatory
    DESCRIPTION
             ""
    ::= { dax 304 }

  daxConfigActiveResourceDivider OBJECT-TYPE
    SYNTAX  INTEGER 
    ACCESS  read-only
    STATUS  mandatory
    DESCRIPTION
             ""
    ::= { dax 305 }

  daxConfigActiveAppl2Rate OBJECT-TYPE
    SYNTAX  INTEGER
    ACCESS  read-only
    STATUS  mandatory
    DESCRIPTION
             ""
    ::= { dax 306 }

  daxConfigActiveLREFInput OBJECT-TYPE
    SYNTAX  INTEGER {
      lref0-def(0),
      lref0(1),
      lref1(2),
      lref2(4),
      lref3(8),
      lref4(16),
      lref5(32),
      lref6(64),
      lref7(128),
      lrefPair04(17),
      lrefPair15(34),
      lrefPair26(68),
      lrefPair37(136)
      }
    ACCESS  read-only
    STATUS  mandatory
    DESCRIPTION
             ""
    ::= { dax 307 }
  
  daxConfigActiveDppl1Input  OBJECT-TYPE
    SYNTAX  INTEGER {
      mainSelector(0),
      mainDivider(1),
      resourceDivider(2)
      }
    ACCESS  read-only
    STATUS  mandatory
    DESCRIPTION
             ""
    ::= { dax 308 }
  
  daxConfigActiveDppl1Rate  OBJECT-TYPE
    SYNTAX  INTEGER {
      dpll14M(0),
      dpll12M(1)
      }
    ACCESS  read-only
    STATUS  mandatory
    DESCRIPTION
             ""
    ::= { dax 309 }
  
  daxConfigActiveLREFInversion OBJECT-TYPE
    SYNTAX  INTEGER 
    ACCESS  read-only
    STATUS  mandatory
    DESCRIPTION
             ""
    ::= { dax 310 }

  daxConfigActiveDpll2Input OBJECT-TYPE
    SYNTAX  INTEGER 
    ACCESS  read-only
    STATUS  mandatory
    DESCRIPTION
             ""
    ::= { dax 311 }
  daxConfigActiveDpll2Rate OBJECT-TYPE
    SYNTAX  INTEGER 
    ACCESS  read-only
    STATUS  mandatory
    DESCRIPTION
             ""
    ::= { dax 312 }

  daxConfigActiveNetref1DividerIn OBJECT-TYPE
    SYNTAX  INTEGER {
      selectorOutput(0),
      externalInput(1)
    }
    ACCESS  read-only
    STATUS  mandatory
    DESCRIPTION
             ""
    ::= { dax 313 }

  daxConfigActiveNetref1SelectIn OBJECT-TYPE
    SYNTAX  INTEGER {
      osc2M(0),
      osc16M(1),
      netref2(2),
      lrefInput(4),
      oscXtal2(8)
    }
    ACCESS  read-only
    STATUS  mandatory
    DESCRIPTION
             ""
    ::= { dax 314 }

  daxConfigActiveNetref1Divider  OBJECT-TYPE
    SYNTAX  INTEGER 
    ACCESS  read-only
    STATUS  mandatory
    DESCRIPTION
             ""
    ::= { dax 315 }

  daxConfigActiveNetref1Select  OBJECT-TYPE
    SYNTAX  INTEGER {
      lref0-def(0),
      lref0(1),
      lref1(2),
      lref2(4),
      lref3(8),
      lref4(16),
      lref5(32),
      lref6(64),
      lref7(128)
    }
    ACCESS  read-only
    STATUS  mandatory
    DESCRIPTION
             ""
    ::= { dax 316 }

  daxConfigActiveNetref2DividerIn OBJECT-TYPE
    SYNTAX  INTEGER {
      selectorOutput(0),
      externalInput(1)
    }
    ACCESS  read-only
    STATUS  mandatory
    DESCRIPTION
             ""
    ::= { dax 317 }

  daxConfigActiveNetref2SelectIn OBJECT-TYPE
    SYNTAX  INTEGER {
      osc2M(0),
      osc16M(1),
      netref2(2),
      lrefInput(4),
      oscXtal2(8)
    }
    ACCESS  read-only
    STATUS  mandatory
    DESCRIPTION
             ""
    ::= { dax 318 }

  daxConfigActiveNetref2Divider  OBJECT-TYPE
    SYNTAX  INTEGER 
    ACCESS  read-only
    STATUS  mandatory
    DESCRIPTION
             ""
    ::= { dax 319 }

  daxConfigActiveNetref2Select  OBJECT-TYPE
    SYNTAX  INTEGER {
      lref0-def(0),
      lref0(1),
      lref1(2),
      lref2(4),
      lref3(8),
      lref4(16),
      lref5(32),
      lref6(64),
      lref7(128)
    }
    ACCESS  read-only
    STATUS  mandatory
    DESCRIPTION
             ""
    ::= { dax 320 }
  

  daxConfigActiveHClockEn  OBJECT-TYPE
    SYNTAX  INTEGER {
      disABClk(0),
      enAClk(1),
      enBClk(2),
      enABClk(3)
    }
    ACCESS  read-only
    STATUS  mandatory
    DESCRIPTION
             ""
    ::= { dax 330 }

  daxConfigActiveCClockEn  OBJECT-TYPE
    SYNTAX  INTEGER {
      disCompClk(0),
      enCClkInd(1),
      enAllCCLK(2)
    }
    ACCESS  read-only
    STATUS  mandatory
    DESCRIPTION
             ""
    ::= { dax 331 }

  daxConfigActiveNetref2En OBJECT-TYPE
    SYNTAX  INTEGER {
      disable(0),
      enable(1)
    }
    ACCESS  read-only
    STATUS  mandatory
    DESCRIPTION
             ""
    ::= { dax 332 }

  daxConfigActiveNetref1En OBJECT-TYPE
    SYNTAX  INTEGER {
      disable(0),
      enable(1)
    }
    ACCESS  read-only
    STATUS  mandatory
    DESCRIPTION
             ""
    ::= { dax 333 }

  daxConfigActiveFrCompEn OBJECT-TYPE
    SYNTAX  INTEGER {
      disable(0),
      enable(1)
    }
    ACCESS  read-only
    STATUS  mandatory
    DESCRIPTION
             ""
    ::= { dax 334 }

  daxConfigActiveCompClock OBJECT-TYPE
    SYNTAX  INTEGER {
      c-clkDisable(0),
      enHMVIP(1),
      enMVIP(2),
      enHMVIPAll(3),
      enSCbusClk(4)
    }
    ACCESS  read-only
    STATUS  mandatory
    DESCRIPTION
             ""
    ::= { dax 335 }

  daxConfigActiveC8AOutRate  OBJECT-TYPE
    SYNTAX  INTEGER {
      ctC8A-8M(0),
      ctC8A-4M(1)
    }
    ACCESS  read-only
    STATUS  mandatory
    DESCRIPTION
             ""
    ::= { dax 336 }

  daxConfigActiveC8BOutRate OBJECT-TYPE
    SYNTAX  INTEGER {
      ctC8B-8M(0),
      ctC8B-4M(1)
    }
    ACCESS  read-only
    STATUS  mandatory
    DESCRIPTION
             ""
    ::= { dax 337 }

  daxConfigActiveTClkRate  OBJECT-TYPE
    SYNTAX  INTEGER {
      tclkDisable(0),
      oscXTAL1(1),
      oscXTAL2(2),
      oscXTAL1Inv(17),
      oscXTAL2Inv(18),
      dpll2(32),
      appl1(33),
      apll2(34),
      dpll2Inv(48),
      apll1Inv(49),
      apll2Inv(50),
      gen2048(64),
      gen4096(65),
      gen8192(66),
      gen16384(68),
      gen32768(72),
      gen2048Inv(80),
      gen4096Inv(81),
      gen8192Inv(82),
      gen16384Inv(84),
      gen32768Inv(88),
      genFrame(128),
      ct-netref1(129),
      ct-netref2(130),
      genFrameInv(144),
      ct-netref1Inv(145),
      ct-netref2Inv(146)
    }
    ACCESS  read-only
    STATUS  mandatory
    DESCRIPTION
             ""
    ::= { dax 338 }

  daxConfigActiveLSC0Rate  OBJECT-TYPE
    SYNTAX  INTEGER {
      lscClkDisable(0),
      oscXTAL1(1),
      oscXTAL1Inv(17),
      gen2048(64),
      gen4096(65),
      gen8192(66),
      gen16384(68),
      gen32768(72),
      gen2048Inv(80),
      gen4096Inv(81),
      gen8192Inv(82),
      gen16384Inv(84),
      gen32768Inv(88),
      genFrame(128),
      ct-netref1(129),
      ct-netref2(130),
      genFrameInv(144),
      ct-netref1Inv(145),
      ct-netref2Inv(146)
    }
    ACCESS  read-only
    STATUS  mandatory
    DESCRIPTION
             ""
    ::= { dax 339 }

  daxConfigActiveLSC1Rate  OBJECT-TYPE
    SYNTAX  INTEGER {
      lscClkDisable(0),
      oscXTAL1(1),
      oscXTAL1Inv(17),
      gen2048(64),
      gen4096(65),
      gen8192(66),
      gen16384(68),
      gen32768(72),
      gen2048Inv(80),
      gen4096Inv(81),
      gen8192Inv(82),
      gen16384Inv(84),
      gen32768Inv(88),
      genFrame(128),
      ct-netref1(129),
      ct-netref2(130),
      genFrameInv(144),
      ct-netref1Inv(145),
      ct-netref2Inv(146)
    }
    ACCESS  read-only
    STATUS  mandatory
    DESCRIPTION
             ""
    ::= { dax 340 }

  daxConfigActiveLSC2Rate OBJECT-TYPE
    SYNTAX  INTEGER {
      lscClkDisable(0),
      oscXTAL1(1),
      oscXTAL1Inv(17),
      gen2048(64),
      gen4096(65),
      gen8192(66),
      gen16384(68),
      gen32768(72),
      gen2048Inv(80),
      gen4096Inv(81),
      gen8192Inv(82),
      gen16384Inv(84),
      gen32768Inv(88),
      genFrame(128),
      ct-netref1(129),
      ct-netref2(130),
      genFrameInv(144),
      ct-netref1Inv(145),
      ct-netref2Inv(146)
    }
    ACCESS  read-only
    STATUS  mandatory
    DESCRIPTION
             ""
    ::= { dax 341 }

  daxConfigActiveLSC3Rate  OBJECT-TYPE
    SYNTAX  INTEGER {
      lscClkDisable(0),
      oscXTAL1(1),
      oscXTAL1Inv(17),
      gen2048(64),
      gen4096(65),
      gen8192(66),
      gen16384(68),
      gen32768(72),
      gen2048Inv(80),
      gen4096Inv(81),
      gen8192Inv(82),
      gen16384Inv(84),
      gen32768Inv(88),
      genFrame(128),
      ct-netref1(129),
      ct-netref2(130),
      genFrameInv(144),
      ct-netref1Inv(145),
      ct-netref2Inv(146)
    }
    ACCESS  read-only
    STATUS  mandatory
    DESCRIPTION
             ""
    ::= { dax 342 }


  daxConfigInActiveMainInput OBJECT-TYPE
    SYNTAX  INTEGER {
      oscillator(0),
      netref1(17),
      netref2(18),
      lrefIndiv(33),
      lrefPaired(34),
      h110BusA(65),
      h110BusB(66),
      mc1R(68),
      mc1L(72),
      mvipC2(128),
      mvipC4(129),
      sc2M(132),
      sc4M(136)
      }
    ACCESS  read-only
    STATUS  mandatory
    DESCRIPTION
             ""
    ::= { dax 400 }

  daxConfigInActiveMainDivider OBJECT-TYPE
    SYNTAX  INTEGER 
    ACCESS  read-only
    STATUS  mandatory
    DESCRIPTION
             ""
    ::= { dax 401 }

  daxConfigInActiveAppl1Input OBJECT-TYPE
    SYNTAX  INTEGER {
      oscDiv4(0),
      mainDivOut(1),
      resourceDivOut(2),
      dpll1Out(4),
      priRefIn(8)
      }
    ACCESS  read-only
    STATUS  mandatory
    DESCRIPTION
             ""
    ::= { dax 402 }

  daxConfigInActiveAppl1Rate OBJECT-TYPE
    SYNTAX  INTEGER {
      multBy16(0),
      multBy32(1)
      }
    ACCESS  read-only
    STATUS  mandatory
    DESCRIPTION
             ""
    ::= { dax 403 }

  daxConfigInActiveMainInversion OBJECT-TYPE
    SYNTAX  INTEGER 
    ACCESS  read-only
    STATUS  mandatory
    DESCRIPTION
             ""
    ::= { dax 404 }

  daxConfigInActiveResourceDivider OBJECT-TYPE
    SYNTAX  INTEGER 
    ACCESS  read-only
    STATUS  mandatory
    DESCRIPTION
             ""
    ::= { dax 405 }

  daxConfigInActiveAppl2Rate OBJECT-TYPE
    SYNTAX  INTEGER
    ACCESS  read-only
    STATUS  mandatory
    DESCRIPTION
             ""
    ::= { dax 406 }

  daxConfigInActiveLREFInput OBJECT-TYPE
    SYNTAX  INTEGER {
      lref0-def(0),
      lref0(1),
      lref1(2),
      lref2(4),
      lref3(8),
      lref4(16),
      lref5(32),
      lref6(64),
      lref7(128),
      lrefPair04(17),
      lrefPair15(34),
      lrefPair26(68),
      lrefPair37(136)
      }
    ACCESS  read-only
    STATUS  mandatory
    DESCRIPTION
             ""
    ::= { dax 407 }
  
  daxConfigInActiveDppl1Input  OBJECT-TYPE
    SYNTAX  INTEGER {
      mainSelector(0),
      mainDivider(1),
      resourceDivider(2)
      }
    ACCESS  read-only
    STATUS  mandatory
    DESCRIPTION
             ""
    ::= { dax 408 }
  
  daxConfigInActiveDppl1Rate  OBJECT-TYPE
    SYNTAX  INTEGER {
      dpll14M(0),
      dpll12M(1)
      }
    ACCESS  read-only
    STATUS  mandatory
    DESCRIPTION
             ""
    ::= { dax 409 }
  
  daxConfigInActiveLREFInversion OBJECT-TYPE
    SYNTAX  INTEGER 
    ACCESS  read-only
    STATUS  mandatory
    DESCRIPTION
             ""
    ::= { dax 410 }

  daxConfigInActiveDpll2Input OBJECT-TYPE
    SYNTAX  INTEGER 
    ACCESS  read-only
    STATUS  mandatory
    DESCRIPTION
             ""
    ::= { dax 411 }
  daxConfigInActiveDpll2Rate OBJECT-TYPE
    SYNTAX  INTEGER 
    ACCESS  read-only
    STATUS  mandatory
    DESCRIPTION
             ""
    ::= { dax 412 }

  daxConfigInActiveNetref1DividerIn OBJECT-TYPE
    SYNTAX  INTEGER {
      selectorOutput(0),
      externalInput(1)
    }
    ACCESS  read-only
    STATUS  mandatory
    DESCRIPTION
             ""
    ::= { dax 413 }

  daxConfigInActiveNetref1SelectIn OBJECT-TYPE
    SYNTAX  INTEGER {
      osc2M(0),
      osc16M(1),
      netref2(2),
      lrefInput(4),
      oscXtal2(8)
    }
    ACCESS  read-only
    STATUS  mandatory
    DESCRIPTION
             ""
    ::= { dax 414 }

  daxConfigInActiveNetref1Divider  OBJECT-TYPE
    SYNTAX  INTEGER 
    ACCESS  read-only
    STATUS  mandatory
    DESCRIPTION
             ""
    ::= { dax 415 }

  daxConfigInActiveNetref1Select  OBJECT-TYPE
    SYNTAX  INTEGER {
      lref0-def(0),
      lref0(1),
      lref1(2),
      lref2(4),
      lref3(8),
      lref4(16),
      lref5(32),
      lref6(64),
      lref7(128)
    }
    ACCESS  read-only
    STATUS  mandatory
    DESCRIPTION
             ""
    ::= { dax 416 }

  daxConfigInActiveNetref2DividerIn OBJECT-TYPE
    SYNTAX  INTEGER {
      selectorOutput(0),
      externalInput(1)
    }
    ACCESS  read-only
    STATUS  mandatory
    DESCRIPTION
             ""
    ::= { dax 417 }

  daxConfigInActiveNetref2SelectIn OBJECT-TYPE
    SYNTAX  INTEGER {
      osc2M(0),
      osc16M(1),
      netref2(2),
      lrefInput(4),
      oscXtal2(8)
    }
    ACCESS  read-only
    STATUS  mandatory
    DESCRIPTION
             ""
    ::= { dax 418 }

  daxConfigInActiveNetref2Divider  OBJECT-TYPE
    SYNTAX  INTEGER 
    ACCESS  read-only
    STATUS  mandatory
    DESCRIPTION
             ""
    ::= { dax 419 }

  daxConfigInActiveNetref2Select  OBJECT-TYPE
    SYNTAX  INTEGER {
      lref0-def(0),
      lref0(1),
      lref1(2),
      lref2(4),
      lref3(8),
      lref4(16),
      lref5(32),
      lref6(64),
      lref7(128)
    }
    ACCESS  read-only
    STATUS  mandatory
    DESCRIPTION
             ""
    ::= { dax 420 }
  

  daxConfigInActiveHClockEn  OBJECT-TYPE
    SYNTAX  INTEGER {
      disABClk(0),
      enAClk(1),
      enBClk(2),
      enABClk(3)
    }
    ACCESS  read-only
    STATUS  mandatory
    DESCRIPTION
             ""
    ::= { dax 430 }

  daxConfigInActiveCClockEn  OBJECT-TYPE
    SYNTAX  INTEGER {
      disCompClk(0),
      enCClkInd(1),
      enAllCCLK(2)
    }
    ACCESS  read-only
    STATUS  mandatory
    DESCRIPTION
             ""
    ::= { dax 431 }

  daxConfigInActiveNetref2En OBJECT-TYPE
    SYNTAX  INTEGER {
      disable(0),
      enable(1)
    }
    ACCESS  read-only
    STATUS  mandatory
    DESCRIPTION
             ""
    ::= { dax 432 }

  daxConfigInActiveNetref1En OBJECT-TYPE
    SYNTAX  INTEGER {
      disable(0),
      enable(1)
    }
    ACCESS  read-only
    STATUS  mandatory
    DESCRIPTION
             ""
    ::= { dax 433 }

  daxConfigInActiveFrCompEn OBJECT-TYPE
    SYNTAX  INTEGER {
      disable(0),
      enable(1)
    }
    ACCESS  read-only
    STATUS  mandatory
    DESCRIPTION
             ""
    ::= { dax 434 }

  daxConfigInActiveCompClock OBJECT-TYPE
    SYNTAX  INTEGER {
      c-clkDisable(0),
      enHMVIP(1),
      enMVIP(2),
      enHMVIPAll(3),
      enSCbusClk(4)
    }
    ACCESS  read-only
    STATUS  mandatory
    DESCRIPTION
             ""
    ::= { dax 435 }

  daxConfigInActiveC8AOutRate  OBJECT-TYPE
    SYNTAX  INTEGER {
      ctC8A-8M(0),
      ctC8A-4M(1)
    }
    ACCESS  read-only
    STATUS  mandatory
    DESCRIPTION
             ""
    ::= { dax 436 }

  daxConfigInActiveC8BOutRate OBJECT-TYPE
    SYNTAX  INTEGER {
      ctC8B-8M(0),
      ctC8B-4M(1)
    }
    ACCESS  read-only
    STATUS  mandatory
    DESCRIPTION
             ""
    ::= { dax 437 }

  daxConfigInActiveTClkRate  OBJECT-TYPE
    SYNTAX  INTEGER {
      tclkDisable(0),
      oscXTAL1(1),
      oscXTAL2(2),
      oscXTAL1Inv(17),
      oscXTAL2Inv(18),
      dpll2(32),
      appl1(33),
      apll2(34),
      dpll2Inv(48),
      apll1Inv(49),
      apll2Inv(50),
      gen2048(64),
      gen4096(65),
      gen8192(66),
      gen16384(68),
      gen32768(72),
      gen2048Inv(80),
      gen4096Inv(81),
      gen8192Inv(82),
      gen16384Inv(84),
      gen32768Inv(88),
      genFrame(128),
      ct-netref1(129),
      ct-netref2(130),
      genFrameInv(144),
      ct-netref1Inv(145),
      ct-netref2Inv(146)
    }
    ACCESS  read-only
    STATUS  mandatory
    DESCRIPTION
             ""
    ::= { dax 438 }

  daxConfigInActiveLSC0Rate  OBJECT-TYPE
    SYNTAX  INTEGER {
      lscClkDisable(0),
      oscXTAL1(1),
      oscXTAL1Inv(17),
      gen2048(64),
      gen4096(65),
      gen8192(66),
      gen16384(68),
      gen32768(72),
      gen2048Inv(80),
      gen4096Inv(81),
      gen8192Inv(82),
      gen16384Inv(84),
      gen32768Inv(88),
      genFrame(128),
      ct-netref1(129),
      ct-netref2(130),
      genFrameInv(144),
      ct-netref1Inv(145),
      ct-netref2Inv(146)
    }
    ACCESS  read-only
    STATUS  mandatory
    DESCRIPTION
             ""
    ::= { dax 439 }

  daxConfigInActiveLSC1Rate  OBJECT-TYPE
    SYNTAX  INTEGER {
      lscClkDisable(0),
      oscXTAL1(1),
      oscXTAL1Inv(17),
      gen2048(64),
      gen4096(65),
      gen8192(66),
      gen16384(68),
      gen32768(72),
      gen2048Inv(80),
      gen4096Inv(81),
      gen8192Inv(82),
      gen16384Inv(84),
      gen32768Inv(88),
      genFrame(128),
      ct-netref1(129),
      ct-netref2(130),
      genFrameInv(144),
      ct-netref1Inv(145),
      ct-netref2Inv(146)
    }
    ACCESS  read-only
    STATUS  mandatory
    DESCRIPTION
             ""
    ::= { dax 440 }

  daxConfigInActiveLSC2Rate OBJECT-TYPE
    SYNTAX  INTEGER {
      lscClkDisable(0),
      oscXTAL1(1),
      oscXTAL1Inv(17),
      gen2048(64),
      gen4096(65),
      gen8192(66),
      gen16384(68),
      gen32768(72),
      gen2048Inv(80),
      gen4096Inv(81),
      gen8192Inv(82),
      gen16384Inv(84),
      gen32768Inv(88),
      genFrame(128),
      ct-netref1(129),
      ct-netref2(130),
      genFrameInv(144),
      ct-netref1Inv(145),
      ct-netref2Inv(146)
    }
    ACCESS  read-only
    STATUS  mandatory
    DESCRIPTION
             ""
    ::= { dax 441 }

  daxConfigInActiveLSC3Rate  OBJECT-TYPE
    SYNTAX  INTEGER {
      lscClkDisable(0),
      oscXTAL1(1),
      oscXTAL1Inv(17),
      gen2048(64),
      gen4096(65),
      gen8192(66),
      gen16384(68),
      gen32768(72),
      gen2048Inv(80),
      gen4096Inv(81),
      gen8192Inv(82),
      gen16384Inv(84),
      gen32768Inv(88),
      genFrame(128),
      ct-netref1(129),
      ct-netref2(130),
      genFrameInv(144),
      ct-netref1Inv(145),
      ct-netref2Inv(146)
    }
    ACCESS  read-only
    STATUS  mandatory
    DESCRIPTION
             ""
    ::= { dax 442 }

  daxConfigFallbackSelect OBJECT-TYPE
    SYNTAX  INTEGER {
      disable(0),
      enable(1)
    }
    ACCESS  read-write
    STATUS  mandatory
    DESCRIPTION
             ""
    ::= { dax 450 }


daxMSWClockMainRef OBJECT-TYPE
    SYNTAX  INTEGER {
       internal(200),
       system(600),
       wan(602)
    }
    ACCESS  read-write
    STATUS  mandatory
    DESCRIPTION
             "Master: This defines the clock source from which the system
              will base its timing.  Secondary: This defines the clock source
              from which the system will base its timing in the event of
              a complete failure of the master.  Slave: This defines the 
              clock source which will be driven to the NETREF #1."
    ::= { dax 500 }

  daxMSWClockFallbackRef OBJECT-TYPE
    SYNTAX  INTEGER {
       internal(200),
       system(600),
       wan(602)
    }
    ACCESS  read-write
    STATUS  mandatory
    DESCRIPTION
             "Master: This defines the clock source from which the system
              will base its timing if the MainRef goes bad.  Secondary: not used.
              Slave: This defines the clock source which will be driven to
              the NETREF #2."
    ::= { dax 501 }





  --*************************************************************************
  --*************************************************************************
  --                                 DSP Manager
  --*************************************************************************
  --*************************************************************************

  dspDetected OBJECT-TYPE
    SYNTAX      INTEGER
    ACCESS      read-only
    STATUS      mandatory
    DESCRIPTION "Number of DSPs detected in the system."
    ::= { dsp 1 }

  dspAvailable OBJECT-TYPE
    SYNTAX      INTEGER
    ACCESS      read-only
    STATUS      mandatory
    DESCRIPTION "Number of DSPs available."
    ::= { dsp 2 }

  dspFailed OBJECT-TYPE
    SYNTAX      INTEGER
    ACCESS      read-only
    STATUS      mandatory
    DESCRIPTION "Number of DSPs which are not working."
    ::= { dsp 3 }

  dspSelectMemoryDump OBJECT-TYPE
    SYNTAX      INTEGER
    ACCESS      read-write
    STATUS      mandatory
    DESCRIPTION "Identify a DSP to have its internal memory saved after each
                 call.  This memory collection will automatically halt when
                 two consecutive failed call on that DSP are detected."
    ::= { dsp 4 }
  
  dspSelectPcmDump OBJECT-TYPE
    SYNTAX      INTEGER
    ACCESS      read-write
    STATUS      mandatory
    DESCRIPTION "Identify a DSP to have its PCM signal saved for each
                 call (the first x sec).  This PCM capture will automatically halt
                 when two consecutive failed call on that DSP are detected. 
                 Tis condition of halt might change later on. "
    ::= { dsp 5 }




  dspDspNotAvailable OBJECT-TYPE
    SYNTAX      INTEGER
    ACCESS      read-only
    STATUS      mandatory
    DESCRIPTION "The number of times a request for a DSP resource
                 was rejected due to lack of avaiable DSPs."
    ::= { dsp 7 }

  dspFailurePercent OBJECT-TYPE
    SYNTAX      INTEGER
    ACCESS      read-only
    STATUS      mandatory
    DESCRIPTION "This is a percentage calculated by dividing PostV8
                 failure calls by total calls (Success+PostV8) calls."
    ::= { dsp 8 }

  -- Totals
  dspTotalOriginatingCalls     OBJECT-TYPE SYNTAX INTEGER ACCESS read-only STATUS mandatory DESCRIPTION "" ::= { dsp 20 }
  dspTotalAnsweringCalls       OBJECT-TYPE SYNTAX INTEGER ACCESS read-only STATUS mandatory DESCRIPTION "" ::= { dsp 21 }
  dspTotalSuccessfulConnects   OBJECT-TYPE SYNTAX INTEGER ACCESS read-only STATUS mandatory DESCRIPTION "" ::= { dsp 22 }
  dspTotalFailedConnectPreV8   OBJECT-TYPE SYNTAX INTEGER ACCESS read-only STATUS mandatory DESCRIPTION "" ::= { dsp 23 }
  dspTotalFailedConnectPostV8  OBJECT-TYPE SYNTAX INTEGER ACCESS read-only STATUS mandatory DESCRIPTION "" ::= { dsp 24 }
  dspTotalRemoteRetrains       OBJECT-TYPE SYNTAX INTEGER ACCESS read-only STATUS mandatory DESCRIPTION "" ::= { dsp 25 }
  dspTotalRemoteRenegotiates   OBJECT-TYPE SYNTAX INTEGER ACCESS read-only STATUS mandatory DESCRIPTION "" ::= { dsp 26 }
  dspTotalLocalRenegotiates    OBJECT-TYPE SYNTAX INTEGER ACCESS read-only STATUS mandatory DESCRIPTION "" ::= { dsp 27 }
  dspTotalLocalRetrains        OBJECT-TYPE SYNTAX INTEGER ACCESS read-only STATUS mandatory DESCRIPTION "" ::= { dsp 28 }
  dspTotalWentSuspect          OBJECT-TYPE SYNTAX INTEGER ACCESS read-only STATUS mandatory DESCRIPTION "" ::= { dsp 29 }
  dspTotalSavedFromSuspect     OBJECT-TYPE SYNTAX INTEGER ACCESS read-only STATUS mandatory DESCRIPTION "" ::= { dsp 30 }
  dspTotalRebootDueToFails     OBJECT-TYPE SYNTAX INTEGER ACCESS read-only STATUS mandatory DESCRIPTION "" ::= { dsp 31 }
  dspTotalRebootDueToError     OBJECT-TYPE SYNTAX INTEGER ACCESS read-only STATUS mandatory DESCRIPTION "" ::= { dsp 32 }

  dspModemFirmware OBJECT-TYPE
    SYNTAX  DisplayString (SIZE (0..4))
    ACCESS  read-only 
    STATUS  mandatory 
    DESCRIPTION "Firmware revision of the modem code" 
    ::= { dsp 33 }

  dspDebugEvents OBJECT-TYPE
    SYNTAX  EnabledDisabled
    ACCESS  read-write 
    STATUS  mandatory 
    DESCRIPTION "This option enables the debugging events in the dsp." 
    ::= { dsp 34 }

  --*************************************************************************
  -- Table of individual DSPs

  DspStateType ::= INTEGER {
                  hardwareFailure(1),
                  pendingBoot(2),
                  booting(3),
                  hwReseted(4),
                  swLoaded(5),
                  waitForGroup(6),
                  unavailable(7),
                  reserved(8),
                  suspect(9),
                  available(10)
                }

  DspUseType ::= INTEGER {
                  free(1),
                  inuse(2)
                }

  dspTable OBJECT-TYPE
    SYNTAX      SEQUENCE OF DspEntry
    ACCESS      not-accessible
    STATUS      mandatory
    DESCRIPTION "Table of individual DSPs."
    ::= { dsp 6 }

  dspEntry OBJECT-TYPE
    SYNTAX       DspEntry
    ACCESS       not-accessible
    STATUS       mandatory
    DESCRIPTION  "An entry of a DSP."
    INDEX        { dspIndex }
    ::= { dspTable 1 }

  DspEntry ::=
    SEQUENCE {
      dspIndex                    INTEGER,
      dspStateFirst               DspStateType,
      dspStateSecond              DspStateType,
      dspUseFirst                 DspUseType,
      dspUseSecond                DspUseType,
      dspOriginatingCalls         INTEGER,
      dspAnsweringCalls           INTEGER,
      dspPageRequests             INTEGER,
      dspSuccessfulConnects       INTEGER,
      dspFailedConnectPreV8       INTEGER,
      dspFailedConnectPostV8      INTEGER,
      dspRemoteRetrains           INTEGER,
      dspRemoteRenegotiates       INTEGER,
      dspLocalRenegotiates        INTEGER,
      dspLocalRetrains            INTEGER,
      dspWentSuspect              INTEGER,
      dspSavedFromSuspect         INTEGER,
      dspRebootDueToFails         INTEGER,
      dspRebootDueToError         INTEGER,
      dspReservedA                INTEGER,
      dspReservedB                INTEGER,
      dspDesiredState             INTEGER,
      dspConsecutiveFails         INTEGER,
      dsp1InstConsecutiveFails    INTEGER,
      dsp2InstConsecutiveFails    INTEGER
    }

  dspIndex OBJECT-TYPE
    SYNTAX      INTEGER (1..30)
    ACCESS      read-only
    STATUS      mandatory
    DESCRIPTION "Identification of this DSP."
    ::= { dspEntry 1 }

  dspDesiredState OBJECT-TYPE
    SYNTAX      INTEGER {
                  pendingReboot(1),
                  rebootNow(2),
                  unavailable(3),
                  available(4),
                  availableFirstOnly(17),
                  availableSecondOnly(18),
                  forceDerail(19)
                }
    ACCESS      read-write
    STATUS      mandatory
    DESCRIPTION "The desired change to be made in the status of this DSP."
    ::= { dspEntry 36 }

  dspStateFirst OBJECT-TYPE
    SYNTAX      DspStateType
    ACCESS      read-only
    STATUS      mandatory
    DESCRIPTION "Defines the state that the modem instance is in.  The posisble
                 states are defined as:
    
                   hardwareFailure:    During power up a self test routine detected
                                       a problem with this DPS.  It will not be booted
                                       with code or used for calls.

                   pendingBoot:        Software on this DSP has stopped acting properly.
                                       This DSP will not be used for calls.  At the next
                                       convienent time the DSP will be rebooted.

                   booting:            The DSP has just been loaded with code and we are
                                       now waiting for an indication from the DSP that
                                       the code properly loaded and is running.

                   unavailable:        The instance is fully operational and could be used
                                       to take a call except that the administrator has
                                       indicated that this instance should not be used.

                   reserved:           The instance is fully operational and could be used
                                       to take a call.  But, another DSP in the same boot
                                       group as this one is pendingBoot. Therefore we are
                                       not to use this until the reboot occurs.

                   suspect:            The instance is operational and could be used to take
                                       a call.  But, we have seen a number of consecutive
                                       failures so we are only using this is no available
                                       instances can be found.  A sucessful call will place
                                       this instance back into the available state.

                   available:          The instance is fully operational and can be used to
                                       take a call"
    ::= { dspEntry 2 }


  dspStateSecond OBJECT-TYPE SYNTAX DspStateType ACCESS read-only STATUS mandatory DESCRIPTION "see dspStateFirst" ::= { dspEntry 4 }

  dspUseFirst  OBJECT-TYPE SYNTAX DspUseType ACCESS read-only STATUS mandatory DESCRIPTION "" ::= { dspEntry 3 }
  dspUseSecond OBJECT-TYPE SYNTAX DspUseType ACCESS read-only STATUS mandatory DESCRIPTION "" ::= { dspEntry 5 }

  -- Debug oriented stats
  dspOriginatingCalls         OBJECT-TYPE SYNTAX INTEGER ACCESS read-only STATUS mandatory DESCRIPTION "" ::= { dspEntry 8 }
  dspAnsweringCalls           OBJECT-TYPE SYNTAX INTEGER ACCESS read-only STATUS mandatory DESCRIPTION "" ::= { dspEntry 9 }
  dspPageRequests             OBJECT-TYPE SYNTAX INTEGER ACCESS read-only STATUS mandatory DESCRIPTION "" ::= { dspEntry 15 }
  dspSuccessfulConnects       OBJECT-TYPE SYNTAX INTEGER ACCESS read-only STATUS mandatory DESCRIPTION "" ::= { dspEntry 16 }
  dspFailedConnectPreV8       OBJECT-TYPE SYNTAX INTEGER ACCESS read-only STATUS mandatory DESCRIPTION "" ::= { dspEntry 17 }
  dspFailedConnectPostV8      OBJECT-TYPE SYNTAX INTEGER ACCESS read-only STATUS mandatory DESCRIPTION "" ::= { dspEntry 14 }
  dspRemoteRetrains           OBJECT-TYPE SYNTAX INTEGER ACCESS read-only STATUS mandatory DESCRIPTION "" ::= { dspEntry 18 }
  dspRemoteRenegotiates       OBJECT-TYPE SYNTAX INTEGER ACCESS read-only STATUS mandatory DESCRIPTION "" ::= { dspEntry 19 }
  dspLocalRenegotiates        OBJECT-TYPE SYNTAX INTEGER ACCESS read-only STATUS mandatory DESCRIPTION "" ::= { dspEntry 20 }
  dspLocalRetrains            OBJECT-TYPE SYNTAX INTEGER ACCESS read-only STATUS mandatory DESCRIPTION "" ::= { dspEntry 21 }
  dspWentSuspect              OBJECT-TYPE SYNTAX INTEGER ACCESS read-only STATUS mandatory DESCRIPTION "" ::= { dspEntry 22 }
  dspSavedFromSuspect         OBJECT-TYPE SYNTAX INTEGER ACCESS read-only STATUS mandatory DESCRIPTION "" ::= { dspEntry 23 }
  dspRebootDueToFails         OBJECT-TYPE SYNTAX INTEGER ACCESS read-only STATUS mandatory DESCRIPTION "" ::= { dspEntry 24 }
  dspRebootDueToError         OBJECT-TYPE SYNTAX INTEGER ACCESS read-only STATUS mandatory DESCRIPTION "" ::= { dspEntry 25 }

  -- Extra one we can use to switch around
  dspReservedA                OBJECT-TYPE SYNTAX INTEGER ACCESS read-only STATUS mandatory DESCRIPTION "" ::= { dspEntry 32 }
  dspReservedB                OBJECT-TYPE SYNTAX INTEGER ACCESS read-only STATUS mandatory DESCRIPTION "" ::= { dspEntry 33 }

  dspConsecutiveFails         OBJECT-TYPE SYNTAX INTEGER ACCESS read-only STATUS mandatory DESCRIPTION "" ::= { dspEntry 37 }
  dsp1InstConsecutiveFails    OBJECT-TYPE SYNTAX INTEGER ACCESS read-only STATUS mandatory DESCRIPTION "" ::= { dspEntry 38 }
  dsp2InstConsecutiveFails    OBJECT-TYPE SYNTAX INTEGER ACCESS read-only STATUS mandatory DESCRIPTION "" ::= { dspEntry 39 }
 

--***************************************************************************
--***************************************************************************
--    Alarm MIB definition
--***************************************************************************
--***************************************************************************

--***************************************************************************
  --                         Alarm SYNTAX Types
--***************************************************************************
  AlarmSeverityType ::= INTEGER {
                  critical(4),
                  major(5),
                  minor(6),
                  informational(7),
                  ignore(8)
                 }

  AlarmResponceType ::= INTEGER {
                  none(0),
                  all(1),
                  critical(4),
                  major(5),
                  minor(6),
                  informational(7)
                 }
  AlarmSyslogPriority ::=
    INTEGER {
      priorityVerbose(5),
      priorityDebug(10),
      priorityInfo(20),
      priorityOddity(40),
      priorityService(60),
      prioritySystem(80),
      priorityDisable(1000)
    }



--***************************************************************************
--    Alarm MIB 
--***************************************************************************
  alarmTotal OBJECT-TYPE
    SYNTAX  INTEGER 
    ACCESS  read-only
    STATUS  mandatory
    DESCRIPTION
             "Total number of alarms currently active in the system"
    ::= { alarm 1 }

  alarmAction OBJECT-TYPE
    SYNTAX  INTEGER {
      noAction(0),
      clearAllAlarms(1)
      }
    ACCESS  read-write
    STATUS  mandatory
    DESCRIPTION
             "This variable can be used to force the system to generate the associated alarm"
    ::= { alarm 2 }

  alarmRelay1 OBJECT-TYPE
    SYNTAX  AlarmResponceType
    ACCESS  read-write
    STATUS  mandatory
    DESCRIPTION
             "This variable is used to determine what type of alarm will cause the 
              relay closure. NOTE: In systems with a single relay, Relay 1 will be
              the supported relay."
    ::= { alarm 3 }

  alarmRelay2 OBJECT-TYPE
    SYNTAX  AlarmResponceType
    ACCESS  read-write
    STATUS  mandatory
    DESCRIPTION
             "This variable is used to determine what type of alarm will cause the 
              relay closure. NOTE: In systems with a single relay, Relay 1 will be
              the supported relay."
    ::= { alarm 4 }

  syslogAlarmPriority OBJECT-TYPE
    SYNTAX      AlarmSyslogPriority
    ACCESS      read-write
    STATUS      mandatory
    DESCRIPTION "Set the syslog priority of the major alarm syslog message,
                 syslog outputs that have a priority less than this value
                 will receive the major alarm syslog message"
    ::= { alarm 5 }

  alarmTrapIp0 OBJECT-TYPE
    SYNTAX      IpAddress
    ACCESS      read-write
    STATUS      mandatory
    DESCRIPTION "The IP address of a host system which is running a
                 SNMP trap deamon.  Major Alarm messages will be sent 
                 to the system. If set to 0.0.0.0 then no trap message
                 will be sent in response to a major alarm"
    ::= { alarm 6 }

  alarmTrapIp1 OBJECT-TYPE
    SYNTAX      IpAddress
    ACCESS      read-write
    STATUS      mandatory
    DESCRIPTION "The IP address of a host system which is running a
                 SNMP trap deamon.  Major Alarm messages will be sent 
                 to the system. If set to 0.0.0.0 then no trap message
                 will be sent in response to a major alarm"
    ::= { alarm 7 }

  alarmTrapIp2 OBJECT-TYPE
    SYNTAX      IpAddress
    ACCESS      read-write
    STATUS      mandatory
    DESCRIPTION "The IP address of a host system which is running a
                 SNMP trap deamon.  Major Alarm messages will be sent 
                 to the system. If set to 0.0.0.0 then no trap message
                 will be sent in response to a major alarm"
    ::= { alarm 8 }

  alarmTrapIp3 OBJECT-TYPE
    SYNTAX      IpAddress
    ACCESS      read-write
    STATUS      mandatory
    DESCRIPTION "The IP address of a host system which is running a
                 SNMP trap deamon.  Major Alarm messages will be sent 
                 to the system. If set to 0.0.0.0 then no trap message
                 will be sent in response to a major alarm"
    ::= { alarm 9 }


  alarmTrapMsg OBJECT-TYPE
    SYNTAX      DisplayString
    ACCESS      read-only
    STATUS      mandatory
    DESCRIPTION "Display string that defines the trap message."
    ::= { alarm 10 }

  alarmBoxState   OBJECT-TYPE
    SYNTAX  INTEGER {
      alarmCriticalState(0),
      alarmMajorState(1),
      alarmMinorState(2),
      alarmClearState(3)
      }
    ACCESS  read-only
    STATUS  mandatory
    DESCRIPTION
             "This variable defines the current state of the unit. This variable 
              can be polled at any time to determine the highest outstanding event."
    ::= { alarm 12 }

  alarmSystemState   OBJECT-TYPE
    SYNTAX  INTEGER {
      alarmCriticalState(0),
      alarmMajorState(1),
      alarmMinorState(2),
      alarmClearState(3)
      }
    ACCESS  read-write
    STATUS  mandatory
    DESCRIPTION
             "This variable defines the state of the chassis system and is intended to be
             set by the NMS system monitoring the chassis based system.  Upon change of this 
             variable the resource will attempt to update any other system parameters available to
             reflect the state change. Outputs could include alarm card indicators"
    ::= { alarm 21 }

  alarmPollMode   OBJECT-TYPE
    SYNTAX  INTEGER {
      doNotMonitor(0),
      monitorAlarmCard(1)
      }
    ACCESS  read-write
    STATUS  mandatory
    DESCRIPTION
            "This variable defines whether the resource card will attempt to access the alarm card on
            the IPMI midplane.  Default configuration for this varialbe is doNotMonitor. NOTE: Only one card
            in the chassis should be configured to monitor the alarm card.  If two cards are configured bus contentions 
            could be generated."
    ::= { alarm 20 }

  alarmFanState   OBJECT-TYPE
    SYNTAX  INTEGER {
      alarmFanStateNormal(0),
      alarmFanStateFailed(1),
      alarmFanStateDegrade(2)
      }
    ACCESS  read-only
    STATUS  mandatory
    DESCRIPTION
            "This variable reflects the state of the fans in the system.  This variable is only accessable
            if the resource card is set to the monitor mode as defined by the alarmPollState variable and the
            chassis based system includes an alarm card that would gather information on the state of the fans"
    ::= { alarm 22 }

  alarmPowerState   OBJECT-TYPE
    SYNTAX  INTEGER {
      alarmPowerStateNormal(0),
      alarmPowerStateFailed(1),
      alarmPowerStateDegrade(2)
      }
    ACCESS  read-only
    STATUS  mandatory
    DESCRIPTION
            "This variable reflects the state of the power supplies in the system.  This variable is only accessable
            if the resource card is set to the monitor mode as defined by the alarmPollState variable and the
            chassis based system includes an alarm card that would gather information on the state of the power supplies"
    ::= { alarm 23 }

  alarmTempState   OBJECT-TYPE
    SYNTAX  INTEGER {
      alarmTempStateNormal(0),
      alarmTempStateFailed(1)
      }
    ACCESS  read-only
    STATUS  mandatory
    DESCRIPTION
            "This variable reflects the state of the temp. monitor in the system.  This variable is only accessable
            if the resource card is set to the monitor mode as defined by the alarmPollState variable and the
            chassis based system includes an alarm card that would gather information on the state of the temp. monitor"
    ::= { alarm 24 }


  alarmTrap TRAP-TYPE
    ENTERPRISE alarm
    VARIABLES  { alarmTrapMsg }
    DESCRIPTION
       "This trap message will be sent as defined by the alarm mib. Major and minor
        trap messages are defined above."
    ::= 1


  alarmDefTable OBJECT-TYPE
    SYNTAX  SEQUENCE OF AlarmDefEntry
    ACCESS  not-accessible
    STATUS  mandatory
    DESCRIPTION
	          ""
    ::= { alarm 100 }

  alarmDefEntry OBJECT-TYPE
    SYNTAX  AlarmDefEntry
    ACCESS  not-accessible
    STATUS  mandatory
    DESCRIPTION
            "Each entry in the table defines a single alarm that the box will generate."
    INDEX   { alarmDefIndex }
    ::= { alarmDefTable 1 }

  AlarmDefEntry ::=
    SEQUENCE {
    alarmDefIndex     Index,
    alarmName         DisplayString,
    alarmSeverity     AlarmSeverityType,
    alarmTicks        TimeTicks,
    alarmGenerate     INTEGER,
    alarmStatus       INTEGER,
    alarmCount        INTEGER
    }

  alarmDefIndex OBJECT-TYPE
    SYNTAX  Index
    ACCESS  read-only
    STATUS  mandatory
    DESCRIPTION
             "the index which identifies the alarm in the table"
    ::= { alarmDefEntry 1 }

  alarmName OBJECT-TYPE
    SYNTAX      DisplayString
    ACCESS      read-only
    STATUS      mandatory
    DESCRIPTION "String describing the alarm"
    ::= { alarmDefEntry 2 }

  alarmSeverity OBJECT-TYPE
    SYNTAX  AlarmSeverityType
    ACCESS  read-write
    STATUS  mandatory
    DESCRIPTION
             "this variable allows the user to select the type of alarm that 
              is generated by the specified event"
    ::= { alarmDefEntry 3 }

  alarmTicks OBJECT-TYPE
    SYNTAX      TimeTicks
    ACCESS      read-only
    STATUS      mandatory
    DESCRIPTION "Timestamp indicating the amount of time since this alarm was reported"
    ::= { alarmDefEntry 4 }

  alarmGenerate   OBJECT-TYPE
    SYNTAX  INTEGER {
      noAction(0),
      generateAlarm(1),
      clearAlarm(2)
      }
    ACCESS  read-write
    STATUS  mandatory
    DESCRIPTION
             "Setting this variable will cause the specified alarm to be set as if
              the alarm event had occured internally"
    ::= { alarmDefEntry 5 }

  alarmStatus   OBJECT-TYPE
    SYNTAX  INTEGER {
      inactive(0),
      active(1)
      }
    ACCESS  read-only
    STATUS  mandatory
    DESCRIPTION
             "Status of the current alarm"
    ::= { alarmDefEntry 6 }

  alarmCount OBJECT-TYPE
    SYNTAX  INTEGER
    ACCESS  read-only
    STATUS  mandatory
    DESCRIPTION
             "The number of times that this alarm has occured"
    ::= { alarmDefEntry 7 }

  --*************************************************************************
  --*************************************************************************
  --*************************************************************************
  -- DNIS mibs

  --*************************************************************************
  --*************************************************************************
  -- DNIS pool discriminator table

  dnisPoolTable OBJECT-TYPE
    SYNTAX      SEQUENCE OF  DnisPoolEntry
    ACCESS      not-accessible
    STATUS      mandatory
    DESCRIPTION "Table of Dnis discriminators."
    ::= { dnis 1 }

  dnisPoolEntry OBJECT-TYPE
    SYNTAX        DnisPoolEntry
    ACCESS        not-accessible
    STATUS        mandatory
    DESCRIPTION   "An entry in the table of Dnis discriminators."
    INDEX         { dnisPoolId }
    ::= { dnisPoolTable 1 }

  DnisPoolEntry ::=
    SEQUENCE {
       dnisPoolId                  Index,
       dnisPoolDesrcDialedNumber   DialedNumber,
       dnisPoolDesrcWan            LineIndex,
       dnisPoolAssignedProfile     INTEGER,
       dnisPoolStatus              DnisStatus
       }
  
  dnisPoolId OBJECT-TYPE
    SYNTAX      Index
    ACCESS      read-write
    STATUS      mandatory
    DESCRIPTION "This is the unique ID for the DNIS pool entry"
    ::= { dnisPoolEntry 1 }

  dnisPoolDesrcDialedNumber OBJECT-TYPE
    SYNTAX      DialedNumber
    ACCESS      read-write
    STATUS      mandatory
    DESCRIPTION "This is part of the discriminator, it identifies the
                 dialed number."
    ::= { dnisPoolEntry 2 }

  dnisPoolDesrcWan OBJECT-TYPE
    SYNTAX      LineIndex
    ACCESS      read-write
    STATUS      mandatory
    DESCRIPTION "This is part of the discriminator, it identifies the WAN port"
    ::= { dnisPoolEntry 3 }

  dnisPoolAssignedProfile OBJECT-TYPE
    SYNTAX      INTEGER
    ACCESS      read-write
    STATUS      mandatory
    DESCRIPTION "This is the ID of the profile which is assigned to the 
                 dsicriminator"
    ::= { dnisPoolEntry 4 }

  dnisPoolStatus OBJECT-TYPE
    SYNTAX      DnisStatus
    ACCESS      read-write
    STATUS      mandatory
    DESCRIPTION "This reflectst the status of the discriminator"
    ::= { dnisPoolEntry 5 }


  --*************************************************************************
    --*************************************************************************
  -- DNIS profile table

  dnisProfileTable OBJECT-TYPE
    SYNTAX      SEQUENCE OF DnisProfileEntry
    ACCESS      not-accessible
    STATUS      mandatory
    DESCRIPTION "Table of Dnis profiles."
    ::= { dnis 2 }

  dnisProfileEntry OBJECT-TYPE
    SYNTAX       DnisProfileEntry
    ACCESS       not-accessible
    STATUS       mandatory
    DESCRIPTION  "An entry in the table of Dnis profiles."
    INDEX        { dnisProfileId }
    ::= { dnisProfileTable 1 }

  DnisProfileEntry ::=
    SEQUENCE {
       dnisProfileId                 Index,
       dnisProfileAssignedIpPool     INTEGER,
       dnisProfileLoginTechnique     LoginTechnique,
       dnisProfileStatus             DnisStatus,
       dnisProfileDOVBS              DovbsConfig,
       dnisProfileServicePort        INTEGER,
       dnisProfileServiceIP          IpAddress
       }

  dnisProfileId OBJECT-TYPE
    SYNTAX      Index
    ACCESS      read-write
    STATUS      mandatory
    DESCRIPTION "This is an unique ID for the profile"
    ::= { dnisProfileEntry 1 }

    dnisProfileAssignedIpPool OBJECT-TYPE
    SYNTAX      INTEGER
    ACCESS      read-write
    STATUS      mandatory
    DESCRIPTION "This is the id of the IP pool which is attached
                 to this profile"
    ::= { dnisProfileEntry 2 }

  dnisProfileLoginTechnique OBJECT-TYPE
    SYNTAX      LoginTechnique
    ACCESS      read-write
    STATUS      mandatory
    DESCRIPTION "This is the login techique as part of a specific profile"
    ::= { dnisProfileEntry 3 }

  dnisProfileStatus OBJECT-TYPE
    SYNTAX      DnisStatus
    ACCESS      read-write
    STATUS      mandatory
    DESCRIPTION "This reflects the status of the profile"
    ::= { dnisProfileEntry 4 }

  dnisProfileDOVBS OBJECT-TYPE
    SYNTAX      DovbsConfig
    ACCESS      read-write
    STATUS      mandatory
    DESCRIPTION "This is the DOVBS configuration of the specific profile"
    ::= { dnisProfileEntry 5 }

  dnisProfileServicePort OBJECT-TYPE
    SYNTAX      INTEGER
    ACCESS      read-write
    STATUS      mandatory
    DESCRIPTION "This is the TCP port used for TCP raw or telnet connections"
    ::= { dnisProfileEntry 6 }

  dnisProfileServiceIP OBJECT-TYPE
    SYNTAX      IpAddress
    ACCESS      read-write
    STATUS      mandatory
    DESCRIPTION "This is the TCP IP address used for TCP raw or telnet connections"
    ::= { dnisProfileEntry 7 }

--*************************************************************************
--*************************************************************************
-- DNIS IP pool table
--*************************************************************************
--*************************************************************************

  dnisIpPoolTable OBJECT-TYPE
    SYNTAX      SEQUENCE OF DnisIpPoolEntry
    ACCESS      not-accessible
    STATUS      mandatory
    DESCRIPTION "Table of Dnis IpPools."
    ::= { dnis 3 }

  dnisIpPoolEntry OBJECT-TYPE
    SYNTAX       DnisIpPoolEntry
    ACCESS       not-accessible
    STATUS       mandatory
    DESCRIPTION  "An entry in the table of ip pools."
    INDEX        { dnisIpPoolId }
    ::= { dnisIpPoolTable 1 }

  DnisIpPoolEntry ::=
    SEQUENCE {
       dnisIpPoolId                 Index,
       dnisIpPool                   IpPool,
       dnisIpPoolStatus             DnisStatus
       }

  dnisIpPoolId OBJECT-TYPE
    SYNTAX      Index
    ACCESS      read-write
    STATUS      mandatory
    DESCRIPTION "This is an unique ID for the ip pool"
    ::= { dnisIpPoolEntry 1 }

  dnisIpPool OBJECT-TYPE
    SYNTAX      IpPool
    ACCESS      read-write
    STATUS      mandatory
    DESCRIPTION "This is the IP pool as entered by the user at the web page"
    ::= { dnisIpPoolEntry 2 }

  dnisIpPoolStatus OBJECT-TYPE
    SYNTAX      DnisStatus
    ACCESS      read-write
    STATUS      mandatory
    DESCRIPTION "This reflects the status of the ip pool"
    ::= { dnisIpPoolEntry 3 }



--*************************************************************************
--*************************************************************************
--                         PPP stuff
--*************************************************************************
--*************************************************************************


  pppDefaultAuthenticationTechnique OBJECT-TYPE
    SYNTAX      INTEGER {
                  none(0),
                  pap(3),
                  chap(4),
                  chapORpap(5)
                }
    ACCESS      read-write
    STATUS      mandatory
    DESCRIPTION "This variable defines the login sequence"
    ::= { ppp 1 }

  pppDefaultAuthenticationSide OBJECT-TYPE
    SYNTAX      INTEGER {
                  local(1),
                  remote(2)
                }
    ACCESS      read-write
    STATUS      mandatory
    DESCRIPTION "This object determines if we are authenticating the remote unit
                 or if the remote unit is authenticating us if authentication is
                 enabled."
    ::= { ppp 2 }

  pppDefaultAuthenticationUsername OBJECT-TYPE
    SYNTAX      AuthenticationString
    ACCESS      read-write
    STATUS      mandatory
    DESCRIPTION "This defines the character string that will be displayed
                at user authentication time to request the users name.
                This should be a ASCII printable string and can include
                charrage returns and line feeds."
    ::= { ppp 3 }

  pppDefaultAuthenticationPassword OBJECT-TYPE
    SYNTAX      AuthenticationString
    ACCESS      read-write
    STATUS      mandatory
    DESCRIPTION "This defines the character string that will be displayed
                at user authentication time to request the users password.
                This should be a ASCII printable string and can include
                charrage returns and line feeds."
    ::= { ppp 4 }
  
  pppDefaultInitialMRU OBJECT-TYPE
    SYNTAX      INTEGER
    ACCESS      read-write
    STATUS      mandatory
    DESCRIPTION "Default setting for Maximum Receive
                 Unit (MRU) if it's not changed by
                 authentication or PPP."
    ::= { ppp 5 }

  pppDefaultIpPool OBJECT-TYPE
    SYNTAX      IpPool
    ACCESS      read-write
    STATUS      mandatory
    DESCRIPTION "String describing the IP address pool."
    ::= { ppp 6 }

  pppDefaultLinkCompression OBJECT-TYPE
    SYNTAX      EnabledDisabled
	ACCESS      read-write
    STATUS      mandatory
    DESCRIPTION "This object enables the PPP link layer address and
                protocol field compression.  When enabled the PPP
                negotiations will DESIRE link compression but may disable
                the compression due the other end of the link.  When
                disabled the PPP negotiations will FORCE no compression
                on the PPP link.

                This is a default setting which may be overridden by
                the authentication of a specific user."
    ::= { ppp 7 }

  pppDefaultMagicNumber OBJECT-TYPE
    SYNTAX      INTEGER {
                  enabled(1),
                  disabled(2)
                }
    ACCESS      read-write
    STATUS      mandatory
    DESCRIPTION "Determines if magic number negotiation should be done."
    ::= { ppp 8 }

  pppDefaultFcsSize OBJECT-TYPE
    SYNTAX      INTEGER
    ACCESS      read-write
    STATUS      mandatory
    DESCRIPTION "The size of the FCS, in bits, the local node
                 will attempt to negotiate for use with the
                 remote node."
    ::= { ppp 9 }

  pppDefaultIpCompression OBJECT-TYPE
    SYNTAX      IpConfigCompression
    ACCESS      read-write
    STATUS      mandatory
    DESCRIPTION "If none(1) then the local node will not
                 attempt to negotiate any IP Compression option.
                 Otherwise, the local node will attempt to
                 negotiate compression mode indicated by the
                 enumerated value. Changing this object will
                 have effect when the link is next restarted."
    REFERENCE   "Section 4.0, Van Jacobson TCP/IP Header
                 Compression of RFC1332."
    ::= { ppp 10 }

  pppDefaultMultiLink OBJECT-TYPE
    SYNTAX      INTEGER
    ACCESS      read-write
    STATUS      mandatory
    DESCRIPTION "Maximum multilink calls per user; 0 disables multilink."
    ::= { ppp 11 }


--*************************************************************************
--*************************************************************************
-- Table of ppp links
--*************************************************************************
--*************************************************************************

  pppTable OBJECT-TYPE
    SYNTAX      SEQUENCE OF PppEntry
    ACCESS      not-accessible
    STATUS      mandatory
    DESCRIPTION "Table of individual ppp links."
    ::= { ppp 100 }

  pppEntry OBJECT-TYPE
    SYNTAX       PppEntry
    ACCESS       not-accessible
    STATUS       mandatory
    DESCRIPTION  "An entry of an active call."
    INDEX        { pppIndex }
    ::= { pppTable 1 }

  PppEntry ::=
    SEQUENCE {
      pppIndex                         Index,
      pppAuthenticationTechnique       INTEGER,
	  pppAuthenticationSide            INTEGER,
	  pppAuthenticationUsername        AuthenticationString,
	  pppAuthenticationPassword        AuthenticationString,
      pppServiceIpAddress              IpAddress,
      pppServiceIpMask                 IpAddress,
      pppIpCompression                 EnabledDisabled,  
      pppLinkCompression               EnabledDisabled,
      pppMagicNumber                   EnabledDisabled,
      pppAccessLevel                   AccessLevel,
      pppStatLocalMRU                  INTEGER,
      pppStatRemoteMRU                 INTEGER,
      pppStatLcpLocalMRRU              INTEGER,
      pppStatLcpRemoteMRRU             INTEGER,
      pppStatLcpAuth                   LcpAuth,
      pppStatLocalToPeerACCMap         OCTET STRING,
      pppStatPeerToLocalACCMap         OCTET STRING,
      pppStatLocalToRemoteProtComp     EnabledDisabled,
      pppStatRemoteToLocalProtComp     EnabledDisabled,
      pppStatLocalToRemoteACComp       EnabledDisabled,
      pppStatRemoteToLocalACComp       EnabledDisabled,
      pppStatTransmitFcsSize           FcsSize,
      pppStatReceiveFcsSize            FcsSize,
      pppIpOperStatus                  INTEGER,
      pppIpLocalToRemoteCompProt       IpConfigCompression,
      pppIpRemoteToLocalCompProt       IpConfigCompression,
      pppIpRemoteMaxSlotId             MaxSlotId,
      pppIpLocalMaxSlotId              MaxSlotId,
      pppActSentOctets                 Counter,
      pppActReceivedOctets             Counter,
      pppActSentDataFrames             INTEGER,
      pppActReceivedDataFrames         INTEGER,
      pppStatBadAddresses              INTEGER,
      pppStatBadControls               Counter,
      pppStatPacketTooLongs            Counter,
      pppActState                      PppStates,
      pppDesiredFunction               INTEGER,
      pppForceNextHop                  IpAddress,
      pppTerminateReason               TerminateReason,
      pppInitialMRU                    INTEGER,
      pppIpFilters                     DisplayString
      }

  pppIndex OBJECT-TYPE
    SYNTAX      Index
    ACCESS      read-only
    STATUS      mandatory
    DESCRIPTION "Unique identification of this active call
                 (use linkTAble.linkTimeSlot.activeIndex)."
    ::= { pppEntry 1 }


  pppAuthenticationTechnique OBJECT-TYPE
    SYNTAX      INTEGER {
                  none(0),
                  pap(3),
                  chap(4),
                  chapORpap(5)
                }
    ACCESS      read-write
    STATUS      mandatory
    DESCRIPTION "This variable defines the login sequence"
    ::= { pppEntry 2 }

  pppAuthenticationSide OBJECT-TYPE
    SYNTAX      INTEGER {
                  local(1),
                  remote(2)
                }
    ACCESS      read-write
    STATUS      mandatory
    DESCRIPTION "This object determines if we are authenticating the remote unit
                 or if the remote unit is authenticating us if authentication is
                 enabled."
    ::= { pppEntry 3 }

  pppAuthenticationUsername OBJECT-TYPE
    SYNTAX      AuthenticationString
    ACCESS      read-write
    STATUS      mandatory
    DESCRIPTION "This defines the character string that will be displayed
                at user authentication time to request the users name.
                This should be a ASCII printable string and can include
                charrage returns and line feeds."
    ::= { pppEntry 4 }

  pppAuthenticationPassword OBJECT-TYPE
    SYNTAX      AuthenticationString
    ACCESS      read-write
    STATUS      mandatory
    DESCRIPTION "This defines the character string that will be displayed
                at user authentication time to request the users password.
                This should be a ASCII printable string and can include
                charrage returns and line feeds."
    ::= { pppEntry 5 }

  pppServiceIpAddress OBJECT-TYPE
    SYNTAX      IpAddress
    ACCESS      read-write
    STATUS      mandatory
    DESCRIPTION "This object defines the IP address which will be used
                for the ppp link."
    ::= { pppEntry 6 }

  pppServiceIpMask OBJECT-TYPE
    SYNTAX      IpAddress
    ACCESS      read-write
    STATUS      mandatory
    DESCRIPTION "This object defines the IP mask which will be used
                for the ppp link."
    ::= { pppEntry 7 }

  pppIpCompression OBJECT-TYPE
    SYNTAX      IpConfigCompression
    ACCESS      read-write
    STATUS      mandatory
    DESCRIPTION "This object defines the IP comprssion for the link."
    ::= { pppEntry 8 }

  pppLinkCompression OBJECT-TYPE
    SYNTAX      EnabledDisabled
    ACCESS      read-write
    STATUS      mandatory
    DESCRIPTION "The compression of the link."
    ::= { pppEntry 9 }


  pppMagicNumber OBJECT-TYPE
    SYNTAX      EnabledDisabled
	ACCESS      read-write
    STATUS      mandatory
    DESCRIPTION "Determines whether magic number is enabled for this link."
    ::= { pppEntry 10 }

  pppAccessLevel OBJECT-TYPE
    SYNTAX      AccessLevel
    ACCESS      read-only
    STATUS      mandatory
    DESCRIPTION "The security level given to this call
                 (usually PASSTHRU)."
    ::= { pppEntry 11 }

  pppStatLocalMRU OBJECT-TYPE
    SYNTAX      INTEGER
    ACCESS      read-only
    STATUS      mandatory
    DESCRIPTION "The current value of the local Maximum Transfer
                 Unit (MRU) for PPP and SLIP."
    ::= { pppEntry 12 }

  pppStatRemoteMRU OBJECT-TYPE
    SYNTAX      INTEGER
    ACCESS      read-only
    STATUS      mandatory
    DESCRIPTION "The current value of the remote Maximum Transfer
                 Unit (MRU) for PPP and SLIP."
    ::= { pppEntry 13 }

  pppStatLcpLocalMRRU OBJECT-TYPE
    SYNTAX      INTEGER
    ACCESS      read-only
    STATUS      mandatory
    DESCRIPTION "Multilink max. receive reconstruction unit
                 for the local device."
    ::= { pppEntry 14 }

  pppStatLcpRemoteMRRU OBJECT-TYPE
    SYNTAX      INTEGER
    ACCESS      read-only
    STATUS      mandatory
    DESCRIPTION "Multilink max. receive reconstruction unit
                 for the remote device."
    ::= { pppEntry 15 }

  pppStatLcpAuth OBJECT-TYPE
    SYNTAX      LcpAuth
    ACCESS      read-only
    STATUS      mandatory
    DESCRIPTION "LCP authentication."
    ::= { pppEntry 16 }

  pppStatLocalToPeerACCMap OBJECT-TYPE
    SYNTAX      OCTET STRING
    ACCESS      read-only
    STATUS      mandatory
    DESCRIPTION "The current value of the ACC Map used for
                 sending packets from the local entity to
                 the remote entity."
    ::= { pppEntry 17 }

  pppStatPeerToLocalACCMap OBJECT-TYPE
    SYNTAX      OCTET STRING
    ACCESS      read-only
    STATUS      mandatory
    DESCRIPTION "The current value of the ACC Map used for
                 sending packets from the remote entity to
                 the local entity."
    ::= { pppEntry 18 }

  pppStatLocalToRemoteProtComp OBJECT-TYPE
    SYNTAX      EnabledDisabled
    ACCESS      read-only
    STATUS      mandatory
    DESCRIPTION "Indicates whether the local entity will
                 use Protocol Compression when transmitting
                 packets to the remote entity."
    ::= { pppEntry 19 }

  pppStatRemoteToLocalProtComp OBJECT-TYPE
    SYNTAX      EnabledDisabled
	ACCESS      read-only
    STATUS      mandatory
    DESCRIPTION "Indicates whether the local entity will
                 use Protocol Compression when transmitting
                 packets to the remote entity."
    ::= { pppEntry 20 }


  pppStatLocalToRemoteACComp OBJECT-TYPE
    SYNTAX      EnabledDisabled
	ACCESS      read-only
    STATUS      mandatory
    DESCRIPTION "Indicates whether the local entity will
                 use Address and Control Compression when
                 transmitting packets to the remote entity."
    ::= { pppEntry 21 }

  pppStatRemoteToLocalACComp OBJECT-TYPE
    SYNTAX      EnabledDisabled
	ACCESS      read-only
    STATUS      mandatory
    DESCRIPTION "Indicates whether the remote entity will
                 use Address and Control Compression when
                 transmitting packets to the local entity."
    ::= { pppEntry 22 }

  pppStatTransmitFcsSize OBJECT-TYPE
    SYNTAX      FcsSize
    ACCESS      read-only
    STATUS      mandatory
    DESCRIPTION "The size of the Frame Check Sequence (FCS) in
                 bits that the local node will generate when
                 sending packets to the remote node."
    ::= { pppEntry 23 }

  pppStatReceiveFcsSize OBJECT-TYPE
    SYNTAX      FcsSize
    ACCESS      read-only
    STATUS      mandatory
    DESCRIPTION "The size of the Frame Check Sequence (FCS) in
                 bits that the local node will generate when
                 sending packets to the remote node."
    ::= { pppEntry 24 }

  pppIpOperStatus OBJECT-TYPE
    SYNTAX      INTEGER
    ACCESS      read-only
    STATUS      mandatory
    DESCRIPTION "Operational status of the call."
    ::= { pppEntry 25 }

  pppIpLocalToRemoteCompProt OBJECT-TYPE
    SYNTAX      IpConfigCompression
    ACCESS      read-only
    STATUS      mandatory
    DESCRIPTION "The IP compression protocol that the local
                 IP entity uses when sending packets to the
                 remote IP entity."
    ::= { pppEntry 26 }

  pppIpRemoteToLocalCompProt OBJECT-TYPE
    SYNTAX      IpConfigCompression
	ACCESS      read-only
    STATUS      mandatory
    DESCRIPTION "The IP compression protocol that the remote
                 IP entity uses when sending packets to the
                 local IP entity."
    ::= { pppEntry 27 }

  pppIpRemoteMaxSlotId OBJECT-TYPE
    SYNTAX      MaxSlotId
    ACCESS      read-only
    STATUS      mandatory
    DESCRIPTION "The Max-Slot-Id parameter that the remote node
                 has advertised and that is in use on the link.
                 If vj-tcp header compression is not in use on
                 the link then the value of this object shall be 0."
    ::= { pppEntry 28 }

  pppIpLocalMaxSlotId OBJECT-TYPE
    SYNTAX      MaxSlotId
    ACCESS      read-only
    STATUS      mandatory
    DESCRIPTION "The Max-Slot-Id parameter that the local node
                 has advertised and that is in use on the link.
                 If vj-tcp header compression is not in use on
                 the link then the value of this object shall be 0."
    ::= { pppEntry 29 }

  pppActSentOctets OBJECT-TYPE
    SYNTAX      Counter
    ACCESS      read-only
    STATUS      mandatory
    DESCRIPTION "The number of octets sent on this call."
    ::= { pppEntry 30 }

  pppActReceivedOctets OBJECT-TYPE
    SYNTAX      Counter
    ACCESS      read-only
    STATUS      mandatory
    DESCRIPTION "The number of octets received on this call."
    ::= { pppEntry 31 }

  pppActSentDataFrames OBJECT-TYPE
    SYNTAX      INTEGER
    ACCESS      read-only
    STATUS      mandatory
    DESCRIPTION "The number of sent packets on this call."
    ::= { pppEntry 32 }

  pppActReceivedDataFrames OBJECT-TYPE
    SYNTAX      INTEGER
    ACCESS      read-only
    STATUS      mandatory
    DESCRIPTION "The number of received packets on this call."
    ::= { pppEntry 33 }

  pppStatBadAddresses OBJECT-TYPE
    SYNTAX      INTEGER
    ACCESS      read-only
    STATUS      mandatory
    DESCRIPTION "Statistics on the link."
    ::= { pppEntry 34 }

  pppStatBadControls OBJECT-TYPE
    SYNTAX      Counter
    ACCESS      read-only
    STATUS      mandatory
    DESCRIPTION "The number of packets received on this call
                 with an incorrect Control Field."
    ::= { pppEntry 35 }

  pppStatPacketTooLongs OBJECT-TYPE
    SYNTAX      Counter
    ACCESS      read-only
    STATUS      mandatory
    DESCRIPTION "The number of received packets that have been
                 discarded because their length exceeded the
                 MRU."
    ::= { pppEntry 36 }

  pppActState OBJECT-TYPE
    SYNTAX      PppStates
    ACCESS      read-write
    STATUS      mandatory
    DESCRIPTION "Indicates current progress and reason for
                 termination."
    ::= { pppEntry 37 }

  pppDesiredFunction OBJECT-TYPE
    SYNTAX  INTEGER {
      ppp(1),
      ppp-bcp(2)
      }
    ACCESS      read-write
    STATUS      mandatory
    DESCRIPTION
                "This is the actual desired kind of ppp protocol."
    ::= { pppEntry 38 }


  pppForceNextHop OBJECT-TYPE
    SYNTAX      IpAddress
    ACCESS      read-write
    STATUS      mandatory
    DESCRIPTION "This object defines the IP address of the interface
                which should be the next hop for the packets - fast routing."
    ::= { pppEntry 39 }

  pppTerminateReason OBJECT-TYPE
    SYNTAX      TerminateReason
    ACCESS      read-only
    STATUS      mandatory
    DESCRIPTION "The reason a link was disconnected."
    ::= { pppEntry 40 }


  pppInitialMRU OBJECT-TYPE
    SYNTAX      INTEGER
    ACCESS      read-write
    STATUS      mandatory
    DESCRIPTION "Initial setting for Maximum Receive
                 Unit (MRU), used for the PPP negotiation."
    ::= { pppEntry 41 }

  pppIpFilters OBJECT-TYPE
    SYNTAX      DisplayString (SIZE (0..64))
    ACCESS      read-write
    STATUS      mandatory
    DESCRIPTION "A maximum of 10 IP Filters to be applied to this interface."
    ::= { pppEntry 42 }


  --*************************************************************************
  --*************************************************************************
  -- Dialout Location table
  --*************************************************************************
  --*************************************************************************

  locationTable OBJECT-TYPE
    SYNTAX      SEQUENCE OF  LocationEntry
    ACCESS      not-accessible
    STATUS      mandatory
    DESCRIPTION "Table of Dialout locations"
    ::= { location 1 }

  locationEntry OBJECT-TYPE
    SYNTAX        LocationEntry
    ACCESS        not-accessible
    STATUS        mandatory
    DESCRIPTION   "An entry in the location table."
    INDEX         { locationId }
    ::= { locationTable 1 }

  LocationEntry ::=
    SEQUENCE { 
       locationId                Index,
       locationName              DisplayString,
       locationUserName          DisplayString,
       locationPassword          DisplayString,
       locationPhoneNumber       DialedNumber,
       locationDestinationIP     IpAddress,
       locationDestinationNet    IpAddress,
       locationConfigMultilink   INTEGER,
       locationConnectType       INTEGER,
       locationConfigRip         EnabledDisabled,
       locationIdleTimeout       INTEGER,
       locationSessionTimeout    INTEGER,
       locationAuthTechnique     INTEGER,
       locationModemProfile      INTEGER,
       locationIpFilters         DisplayString,
       locationStatus            INTEGER,
       locationDodIP             IpAddress,
       locationDodNet            IpAddress
       }

  locationId OBJECT-TYPE
    SYNTAX  Index
    ACCESS  read-only
    STATUS  mandatory
    DESCRIPTION   "This is the index into the location table."
    ::= { locationEntry 1 }

  locationName OBJECT-TYPE
    SYNTAX  DisplayString (SIZE (0..12))
    ACCESS  read-write
    STATUS  mandatory
    DESCRIPTION   "This is the name of the location to dial."
    ::= { locationEntry 2 }

  locationUserName OBJECT-TYPE
    SYNTAX  DisplayString (SIZE (0..32))
    ACCESS  read-write
    STATUS  mandatory
    DESCRIPTION   "This is the username to login to the remote system"
    ::= { locationEntry 3 }

  locationPassword OBJECT-TYPE
    SYNTAX  DisplayString (SIZE (0..32))
    ACCESS  read-write
    STATUS  mandatory
    DESCRIPTION   "This is the password to login to the remote system"
    ::= { locationEntry 4 }

  locationPhoneNumber OBJECT-TYPE
    SYNTAX  DialedNumber
    ACCESS  read-write
    STATUS  mandatory
    DESCRIPTION   "This is the password to login to the remote system"
    ::= { locationEntry 5 }

  locationDestinationIP OBJECT-TYPE
    SYNTAX  IpAddress
    ACCESS  read-write
    STATUS  mandatory
    DESCRIPTION   "This is IP address of the connection"
    ::= { locationEntry 6 }

  locationDestinationNet OBJECT-TYPE
    SYNTAX  IpAddress
    ACCESS  read-write
    STATUS  mandatory
    DESCRIPTION   "This is Netmask of the connection"
    ::= { locationEntry 7 }

  locationConfigMultilink OBJECT-TYPE
    SYNTAX  INTEGER
    ACCESS  read-write
    STATUS  mandatory
    DESCRIPTION   "This is the maximum number of multilink calls for this location."
    ::= { locationEntry 9 }

  locationConnectType OBJECT-TYPE
    SYNTAX  INTEGER{
              manual(0),
              continuous(1),
              dial-on-demand(2)           
            } 
    ACCESS  read-write
    STATUS  mandatory
    DESCRIPTION   "This is the type of connection for this location."
    ::= { locationEntry 10 }

  locationConfigRip OBJECT-TYPE
    SYNTAX  EnabledDisabled
    ACCESS  read-write
    STATUS  mandatory
    DESCRIPTION   "This enables/disables RIP for this location."
    ::= { locationEntry 11 }

  locationIdleTimeout OBJECT-TYPE
    SYNTAX  INTEGER
    ACCESS  read-write
    STATUS  mandatory
    DESCRIPTION   "This is the maximum idle time for the connection."
    ::= { locationEntry 12 }

  locationSessionTimeout OBJECT-TYPE
    SYNTAX  INTEGER
    ACCESS  read-write
    STATUS  mandatory
    DESCRIPTION   "This is the maximum session time for the connection"
    ::= { locationEntry 13 }

  locationAuthTechnique OBJECT-TYPE
    SYNTAX  INTEGER {
             none(0),
             pap(3),
             chap(4)
             }
    ACCESS  read-write
    STATUS  mandatory
    DESCRIPTION   "This determines how to login to the remote"
    ::= { locationEntry 14 }

  locationModemProfile OBJECT-TYPE
    SYNTAX  INTEGER
    ACCESS  read-write
    STATUS  mandatory
    DESCRIPTION   "This describes how to connect to the far end."
    ::= { locationEntry 15 }

  locationIpFilters OBJECT-TYPE
    SYNTAX      DisplayString (SIZE (0..64))
    ACCESS      read-write
    STATUS      mandatory
    DESCRIPTION "A maximum of 10 IP Filters to be applied to this interface."

    ::= { locationEntry 16 }


  locationStatus OBJECT-TYPE
    SYNTAX  INTEGER{
                   idle(1),
                   dial(2),
                   active(3),
                   waitingRedial(4),
                   waitingDemand(5),
                   stop(6),
                   destroy(7)
                   }
    ACCESS  read-write
    STATUS  mandatory
    DESCRIPTION   "This is the status of the location."
    ::= { locationEntry 17 }

  locationDodIP OBJECT-TYPE
    SYNTAX  IpAddress
    ACCESS  read-write
    STATUS  mandatory
    DESCRIPTION   "This is IP address of the connection"
    ::= { locationEntry 18 }

  locationDodNet OBJECT-TYPE
    SYNTAX  IpAddress
    ACCESS  read-write
    STATUS  mandatory
    DESCRIPTION   "This is Netmask of the connection"
    ::= { locationEntry 19 }

  --*************************************************************************
  --*************************************************************************
  -- Modem Profile table
  --*************************************************************************
  --*************************************************************************

  modemTable OBJECT-TYPE
    SYNTAX      SEQUENCE OF  ModemEntry
    ACCESS      not-accessible
    STATUS      mandatory
    DESCRIPTION "Table of modem profiles"
    ::= { modem 1 }

  modemEntry OBJECT-TYPE
    SYNTAX        ModemEntry
    ACCESS        not-accessible
    STATUS        mandatory
    DESCRIPTION   "An entry in the modem profile table."
    INDEX         { modemProfileId }
    ::= { modemTable 1 }

  ModemEntry ::=
    SEQUENCE  { 
              modemProfileId            Index,
              modemType                 INTEGER, 
              modemMaxSpeed             INTEGER,
              modemMinSpeed             INTEGER,
              modemGuardTone            INTEGER, 
              modemCarrierLossDuration  INTEGER, 
              modemRetrain              INTEGER,
              modemTxLevel              INTEGER,
              modemProtocol             INTEGER, 
              modemCompression          INTEGER,
              modemBillingDelay         INTEGER, 
              modemStatus               INTEGER
              }

  modemProfileId OBJECT-TYPE
    SYNTAX  Index
    ACCESS  read-only
    STATUS  mandatory
    DESCRIPTION   "This is the index into the modem profile table."
    ::= { modemEntry 1 }

  modemType OBJECT-TYPE
    SYNTAX  INTEGER {
              digital-64k(1),
              analog-v90(2),
              analog-k56(3),
              analog-v34(4),
              analog-v32(5),
              analog-v22bis(6),
              analog-v22(7),
              analog-v21(8)
              }
    ACCESS      read-write
    STATUS      mandatory
    DESCRIPTION "Specify the modulation to dial out."
    ::= { modemEntry 2 }


  modemMaxSpeed OBJECT-TYPE
    SYNTAX      INTEGER
    ACCESS      read-write
    STATUS      mandatory
    DESCRIPTION "This variable allows the selection of the fastest
                 data rate that will be negotiated."
    ::= { modemEntry 3 }

  modemMinSpeed OBJECT-TYPE
    SYNTAX      INTEGER
    ACCESS      read-write
    STATUS      mandatory
    DESCRIPTION "This variable allows the selection of the slowest
                 data rate that will be negotiated."
    ::= { modemEntry 4 }

  modemGuardTone OBJECT-TYPE
    SYNTAX  INTEGER {
      toneNone(1),
      tone1800(3)
      }
    ACCESS      read-write
    STATUS      mandatory
    DESCRIPTION "Normally a guard tone is not required.  But, one can be
                 inserted.  This operates for Phase Shift Key modulations only."
    ::= { modemEntry 5 }

  modemCarrierLossDuration OBJECT-TYPE
    SYNTAX      INTEGER (1..255)
    ACCESS      read-write
    STATUS      mandatory
    DESCRIPTION "The number of seconds the carrier must be 
                 lost before it is considered the connection dead. A
                 setting above 100 indicates forever."
    ::= { modemEntry 6 }

  modemRetrain OBJECT-TYPE
    SYNTAX      INTEGER {
      none(0),
      retrain(1),
      fallForwardFallBack(2)
      }
    ACCESS      read-write
    STATUS      mandatory
    DESCRIPTION "Allow the modem to monitor the line quality and 
                 request a fallback or retrain for poor quality and a
                 fallforward for good quality."
    ::= { modemEntry 7 }

  modemTxLevel OBJECT-TYPE
    SYNTAX      INTEGER (0..15)
    ACCESS      read-write
    STATUS      mandatory
    DESCRIPTION "This variable should be set with caution; and normally
                 only after talking to a factory representative.  This
                 sets the transmit level power level of the modem.  The
                 scale is 0 (0 dB) to 15 (-15 dB).   Note that larger
                 numbers mean less power."
    ::= { modemEntry 8 }

  modemProtocol OBJECT-TYPE
    SYNTAX      INTEGER {
      direct(0),
      requestV42(1),
      requireV42(2)
      }
    ACCESS      read-write
    STATUS      mandatory
    DESCRIPTION "Selection of the data protocol to use on the modem.
                 This allows the request of or forcing of V42
                 error correction protocol."
    ::= { modemEntry 9 }

  modemCompression OBJECT-TYPE
    SYNTAX      INTEGER {
      direct(0),
      requestV42bis(1),
      requireV42bis(2),
      v44(3)
      }
    ACCESS      read-write
    STATUS      mandatory
    DESCRIPTION "Selection of the data compression protocol to use on 
                 the modem. This allows the request of or forcing of 
                 V42 compression protocol.  This will only be 
                 used if V42 error correction is active."
    ::= { modemEntry 10 }

  modemBillingDelay OBJECT-TYPE
    SYNTAX      INTEGER (0..2)
    ACCESS      read-write
    STATUS      mandatory
    DESCRIPTION "The number of seconds after answering the call during
                 which the modem should remain silent.  On older phone
                 systems the silence time was required to allow billing
                 tones to pass."
    ::= { modemEntry 11 }

  modemStatus OBJECT-TYPE
    SYNTAX      INTEGER {
      valid(1),
      destroy(2)
      }
    ACCESS      read-write
    STATUS      mandatory
    DESCRIPTION "The number of seconds after answering the call during
                 which the modem should remain silent.  On older phone
                 systems the silence time was required to allow billing
                 tones to pass."
    ::= { modemEntry 12 }

  --*************************************************************************
  --*************************************************************************
  -- System Management table
  --*************************************************************************
  --*************************************************************************

  sysMgmtTable OBJECT-TYPE
    SYNTAX      SEQUENCE OF  SysMgmtEntry
    ACCESS      not-accessible
    STATUS      mandatory
    DESCRIPTION "Table Intra-chassis H.110 connections."
    ::= { sysMgmt 1 }

  sysMgmtErrorReport OBJECT-TYPE
    SYNTAX  DisplayString
    ACCESS  read-only
    STATUS  mandatory
    DESCRIPTION "This read only string will show the reason that the last 
                 submission to the in-band connection table was rejected. This
                 string will remain until either another error connection
                 is submitted or until a valid connection is submitted."
    ::= { sysMgmt 2 }

  sysMgmtCliConnection OBJECT-TYPE
    SYNTAX  DisplayString
    ACCESS  read-write
    STATUS  mandatory
    DESCRIPTION "This variable allows the user to input a POH connection into the box. 
                 Use the following convention for adding new connections:
                 IPAddress[w.x.y.z]/GW[1,0]/TX Port:Slot/RX Port:Slot
                 GW = default gateway (1=yes, 0=no)."
    ::= { sysMgmt 3 }

  sysMgmtEntry OBJECT-TYPE
    SYNTAX        SysMgmtEntry
    ACCESS        not-accessible
    STATUS        mandatory
    DESCRIPTION   "An entry in the intra-chassis H.110 connection table."
    INDEX         { sysMgmtConnectionID }
    ::= { sysMgmtTable 1 }

  SysMgmtEntry ::=
    SEQUENCE  { 
              sysMgmtConnectionID       Index,
              sysMgmtPortTx             GSDSLDaxDeviceStreamType,
              sysMgmtPortRx             GSDSLDaxDeviceStreamType,
              sysMgmtSlotTx             INTEGER,
              sysMgmtSlotRx             INTEGER,
              sysMgmtIpAddress          IpAddress,
              sysMgmtStatus             INTEGER,
              sysMgmtRxNoBufferAvailable INTEGER,
              sysMgmtRxDataOverflow      INTEGER,
              sysMgmtRxMessageEnds       INTEGER,
              sysMgmtRxPacketTooLong     INTEGER,
              sysMgmtRxOverflow          INTEGER,
              sysMgmtRxAbort             INTEGER,
              sysMgmtRxBadCrc            INTEGER,
              sysMgmtRxInvalidFrame      INTEGER,
              sysMgmtTxUnderrun          INTEGER,
	            sysMgmtTxOctets            INTEGER,
	            sysMgmtRxOctets            INTEGER,
              sysMgmtResets              INTEGER,
              sysMgmtTxMessageEnds       INTEGER,
              sysMgmtDefaultGateway      INTEGER
              }

  sysMgmtConnectionID OBJECT-TYPE
    SYNTAX  Index
    ACCESS  read-only
    STATUS  mandatory
    DESCRIPTION   "This is the index into the sysMgmt Table."
    ::= { sysMgmtEntry 1 }

  sysMgmtPortTx OBJECT-TYPE
    SYNTAX      GSDSLDaxDeviceStreamType
    ACCESS      read-write
    STATUS      mandatory
    DESCRIPTION "Specify the modulation to dial out."
    ::= { sysMgmtEntry 2 }

  sysMgmtPortRx OBJECT-TYPE
    SYNTAX      GSDSLDaxDeviceStreamType
    ACCESS      read-write
    STATUS      mandatory
    DESCRIPTION "Specify the modulation to dial out."
    ::= { sysMgmtEntry 3 }

  sysMgmtSlotTx OBJECT-TYPE
    SYNTAX  INTEGER (0..'80'h)
    ACCESS  read-write
    STATUS  mandatory
    DESCRIPTION " "
    ::= { sysMgmtEntry 4 }

  sysMgmtSlotRx OBJECT-TYPE
    SYNTAX  INTEGER (0..'80'h)
    ACCESS  read-write
    STATUS  mandatory
    DESCRIPTION " "
    ::= { sysMgmtEntry 5 }

  sysMgmtIpAddress OBJECT-TYPE
    SYNTAX      IpAddress
    ACCESS      read-write
    STATUS      mandatory
    DESCRIPTION " "
    ::= { sysMgmtEntry 6 }

  sysMgmtStatus OBJECT-TYPE
    SYNTAX      INTEGER {
                  down(0),
                  up(1),
                  delete(2)
                  }
    ACCESS      read-write
    STATUS      mandatory
    DESCRIPTION " "
    ::= { sysMgmtEntry 7 }

  sysMgmtRxNoBufferAvailable OBJECT-TYPE
    SYNTAX      INTEGER
    ACCESS      read-only
    STATUS      mandatory
    DESCRIPTION "The number of packets received
               when no buffers were available."
    ::= { sysMgmtEntry 8 }

  sysMgmtRxDataOverflow OBJECT-TYPE
    SYNTAX      INTEGER
    ACCESS      read-only
    STATUS      mandatory
    DESCRIPTION "The number of packets received
  			 with overflow."
    ::= { sysMgmtEntry 9 }

  sysMgmtRxMessageEnds OBJECT-TYPE
    SYNTAX      INTEGER
    ACCESS      read-only
    STATUS      mandatory
    DESCRIPTION "The number of packets received
                 with message ends."
    ::= { sysMgmtEntry 10 }

  sysMgmtRxPacketTooLong OBJECT-TYPE
    SYNTAX      INTEGER
    ACCESS      read-only
    STATUS      mandatory
    DESCRIPTION "The number of packets received
                 that were tool long."
    ::= { sysMgmtEntry 11 }

  sysMgmtRxOverflow OBJECT-TYPE
    SYNTAX      INTEGER
    ACCESS      read-only
    STATUS      mandatory
    DESCRIPTION "The number of packets received
	                with overflow."
    ::= { sysMgmtEntry 12 }

  sysMgmtRxAbort OBJECT-TYPE
    SYNTAX      INTEGER
    ACCESS      read-only
    STATUS      mandatory
    DESCRIPTION "The number of packets received
                 that were aborted."
    ::= { sysMgmtEntry 13 }

  sysMgmtRxBadCrc OBJECT-TYPE
    SYNTAX      INTEGER
    ACCESS      read-only
    STATUS      mandatory
    DESCRIPTION "The number of packets received
                 that had bad CRC."
    ::= { sysMgmtEntry 14 }

  sysMgmtRxInvalidFrame OBJECT-TYPE
    SYNTAX      INTEGER
    ACCESS      read-only
    STATUS      mandatory
    DESCRIPTION "The number of packets received
                 that had an invalid frame."
    ::= { sysMgmtEntry 15 }

  sysMgmtTxUnderrun OBJECT-TYPE
    SYNTAX      INTEGER
    ACCESS      read-only
    STATUS      mandatory
    DESCRIPTION "The number of packets received
                 with underrun."
    ::= { sysMgmtEntry 16 }

  sysMgmtTxOctets OBJECT-TYPE
    SYNTAX      INTEGER
    ACCESS      read-only
    STATUS      mandatory
    DESCRIPTION "Tx bytes/second."
    ::= { sysMgmtEntry 17 }

  sysMgmtRxOctets OBJECT-TYPE
    SYNTAX      INTEGER
    ACCESS      read-only
    STATUS      mandatory
    DESCRIPTION "Rx bytes/second."
    ::= { sysMgmtEntry 18 }

  sysMgmtResets OBJECT-TYPE
    SYNTAX      INTEGER
    ACCESS      read-only
    STATUS      mandatory
    DESCRIPTION "Number of times LMI was reset."
    ::= { sysMgmtEntry 19 }

  sysMgmtTxMessageEnds OBJECT-TYPE
    SYNTAX      INTEGER
    ACCESS      read-only
    STATUS      mandatory
    DESCRIPTION "The number of packets received
                 with message ends."
    ::= { sysMgmtEntry 20 }

  sysMgmtDefaultGateway OBJECT-TYPE
    SYNTAX      INTEGER {
                  no(0),
                  yes(1)
                  }
    ACCESS      read-write
    STATUS      mandatory
    DESCRIPTION "The number of packets received
                 with message ends."
    ::= { sysMgmtEntry 21 }

  END
